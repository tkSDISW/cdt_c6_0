package  'CDT_System Project' {
    import ARCADIA::**; 
    @PackageMeta {
        type = "Project";
    } 
    package  'CDT_System' {
        @PackageMeta {
            type = "SystemEngineering";
        } 
        package  'RPL' {
            @PackageMeta {
                type = "GroupingElementPkg";
            } 
        } 
        package  'Operational Analysis' {
            @PackageMeta {
                type = "OperationalAnalysis";
            } 
            package  'Data' {
                @PackageMeta {
                    type = "DataPkg";
                } 
                item 'ID' : Class { 
                    attribute :>> isAbstract = false; 
                    attribute :>> isFinal = false; 
                    attribute :>> isPrimitive = false; 
                }  
                item 'Athlete ID' : ExchangeItem  { 
                    attribute :>> isAbstract = false; 
                    attribute :>> exchangeMechanism = ExchangeMechanism::SHARED_DATA; 
                    attribute :>> isFinal = false; 
                    item 'ID' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                        ref :>> abstractType = 'CDT_System Project'::'CDT_System'::'Operational Analysis'::'Data'::'ID';
                    } 
                     
                    ref :>> ownedElements =  ('CDT_System Project'::'CDT_System'::'Operational Analysis'::'Data'::'Athlete ID'.'ID'); 
                }  
                item 'Hit' : ExchangeItem  { 
                    attribute :>> isAbstract = false; 
                    attribute :>> exchangeMechanism = ExchangeMechanism::FLOW; 
                    attribute :>> isFinal = false; 
                }  
                item 'Alert' : ExchangeItem  { 
                    attribute :>> isAbstract = false; 
                    attribute :>> exchangeMechanism = ExchangeMechanism::EVENT; 
                    attribute :>> isFinal = false; 
                     
                }  
                item 'Concussion Data' : ExchangeItem  { 
                    attribute :>> isAbstract = false; 
                    attribute :>> exchangeMechanism = ExchangeMechanism::SHARED_DATA; 
                    attribute :>> isFinal = false; 
                     
                }  
                item 'Policy' : ExchangeItem  { 
                    attribute :>> isAbstract = false; 
                    attribute :>> exchangeMechanism = ExchangeMechanism::SHARED_DATA; 
                    attribute :>> isFinal = false; 
                     
                }  
                item 'Report' : ExchangeItem  { 
                    attribute :>> isAbstract = false; 
                    attribute :>> exchangeMechanism = ExchangeMechanism::SHARED_DATA; 
                    attribute :>> isFinal = false; 
                     
                }  
                item 'Power Applied' : ChangeEvent {
                    attribute :>> kind = ChangeEventKind::WHEN;
                }   
            } 
            package  'Operational Entities' {
                @PackageMeta {
                    type = "EntityPkg";
                } 
                part 'Trainer' : Entity  { 
                    attribute :>> isAbstract = false; 
                    attribute :>> isActor = true; 
                    attribute :>> isHuman = true; 
                    allocation '3b944032-aa88-41d6-ba75-9c7995e6c87e' : ComponentFunctionalAllocation
                        allocate function ::> 'CDT_System Project'::'CDT_System'::'Operational Analysis'::'Operational Activities'::'Root Operational Activity'.'Create profiles for Athletes'
                        to component ::> 'CDT_System Project'::'CDT_System'::'Operational Analysis'::'Operational Entities'::'Trainer';
                    perform 'CDT_System Project'::'CDT_System'::'Operational Analysis'::'Operational Activities'::'Root Operational Activity'.'Create profiles for Athletes' ; 
                    allocation 'baf403ed-3edc-4b6c-aa2b-b10cb93b2bfb' : ComponentFunctionalAllocation
                        allocate function ::> 'CDT_System Project'::'CDT_System'::'Operational Analysis'::'Operational Activities'::'Root Operational Activity'.'Create Unique IDs'
                        to component ::> 'CDT_System Project'::'CDT_System'::'Operational Analysis'::'Operational Entities'::'Trainer';
                    perform 'CDT_System Project'::'CDT_System'::'Operational Analysis'::'Operational Activities'::'Root Operational Activity'.'Create Unique IDs' ; 
                    allocation '6e306aa9-fb07-489a-be60-1894d42582e9' : ComponentFunctionalAllocation
                        allocate function ::> 'CDT_System Project'::'CDT_System'::'Operational Analysis'::'Operational Activities'::'Root Operational Activity'.'Provide ID to Athlete'
                        to component ::> 'CDT_System Project'::'CDT_System'::'Operational Analysis'::'Operational Entities'::'Trainer';
                    perform 'CDT_System Project'::'CDT_System'::'Operational Analysis'::'Operational Activities'::'Root Operational Activity'.'Provide ID to Athlete' ; 
                    allocation '35e00554-a3a6-42e1-84bf-315b248508d6' : ComponentFunctionalAllocation
                        allocate function ::> 'CDT_System Project'::'CDT_System'::'Operational Analysis'::'Operational Activities'::'Root Operational Activity'.'Assemble System Components'
                        to component ::> 'CDT_System Project'::'CDT_System'::'Operational Analysis'::'Operational Entities'::'Trainer';
                    perform 'CDT_System Project'::'CDT_System'::'Operational Analysis'::'Operational Activities'::'Root Operational Activity'.'Assemble System Components' ; 
                    allocation '4c287946-231a-4841-bc72-81159837a41c' : ComponentFunctionalAllocation
                        allocate function ::> 'CDT_System Project'::'CDT_System'::'Operational Analysis'::'Operational Activities'::'Root Operational Activity'.'Prep the device for use'
                        to component ::> 'CDT_System Project'::'CDT_System'::'Operational Analysis'::'Operational Entities'::'Trainer';
                    perform 'CDT_System Project'::'CDT_System'::'Operational Analysis'::'Operational Activities'::'Root Operational Activity'.'Prep the device for use' ; 
                    allocation '8b7dd048-326b-41fb-a230-f90dc82f1cfb' : ComponentFunctionalAllocation
                        allocate function ::> 'CDT_System Project'::'CDT_System'::'Operational Analysis'::'Operational Activities'::'Root Operational Activity'.'Recieve Enabled Signal from Athelete Helmut'
                        to component ::> 'CDT_System Project'::'CDT_System'::'Operational Analysis'::'Operational Entities'::'Trainer';
                    perform 'CDT_System Project'::'CDT_System'::'Operational Analysis'::'Operational Activities'::'Root Operational Activity'.'Recieve Enabled Signal from Athelete Helmut' ; 
                    allocation '89f8a6ce-750e-4fe4-92ad-9085f4a8c50b' : ComponentFunctionalAllocation
                        allocate function ::> 'CDT_System Project'::'CDT_System'::'Operational Analysis'::'Operational Activities'::'Root Operational Activity'.'Trainer Recieves Concussion Alert'
                        to component ::> 'CDT_System Project'::'CDT_System'::'Operational Analysis'::'Operational Entities'::'Trainer';
                    perform 'CDT_System Project'::'CDT_System'::'Operational Analysis'::'Operational Activities'::'Root Operational Activity'.'Trainer Recieves Concussion Alert' ; 
                    allocation '2449e927-0200-41df-bb5e-18d3830321ba' : ComponentFunctionalAllocation
                        allocate function ::> 'CDT_System Project'::'CDT_System'::'Operational Analysis'::'Operational Activities'::'Root Operational Activity'.'Data can be reviewed'
                        to component ::> 'CDT_System Project'::'CDT_System'::'Operational Analysis'::'Operational Entities'::'Trainer';
                    perform 'CDT_System Project'::'CDT_System'::'Operational Analysis'::'Operational Activities'::'Root Operational Activity'.'Data can be reviewed' ; 
                    allocation '809b5c3b-80d8-43e4-bba8-39ba3be8e76c' : ComponentFunctionalAllocation
                        allocate function ::> 'CDT_System Project'::'CDT_System'::'Operational Analysis'::'Operational Activities'::'Root Operational Activity'.'Executes Policies'
                        to component ::> 'CDT_System Project'::'CDT_System'::'Operational Analysis'::'Operational Entities'::'Trainer';
                    perform 'CDT_System Project'::'CDT_System'::'Operational Analysis'::'Operational Activities'::'Root Operational Activity'.'Executes Policies' ; 
                    ref :>> ownedFunctionalAllocation =  ('CDT_System Project'::'CDT_System'::'Operational Analysis'::'Operational Entities'::'Trainer'.'3b944032-aa88-41d6-ba75-9c7995e6c87e',
                    'CDT_System Project'::'CDT_System'::'Operational Analysis'::'Operational Entities'::'Trainer'.'baf403ed-3edc-4b6c-aa2b-b10cb93b2bfb',
                    'CDT_System Project'::'CDT_System'::'Operational Analysis'::'Operational Entities'::'Trainer'.'6e306aa9-fb07-489a-be60-1894d42582e9',
                    'CDT_System Project'::'CDT_System'::'Operational Analysis'::'Operational Entities'::'Trainer'.'35e00554-a3a6-42e1-84bf-315b248508d6',
                    'CDT_System Project'::'CDT_System'::'Operational Analysis'::'Operational Entities'::'Trainer'.'4c287946-231a-4841-bc72-81159837a41c',
                    'CDT_System Project'::'CDT_System'::'Operational Analysis'::'Operational Entities'::'Trainer'.'8b7dd048-326b-41fb-a230-f90dc82f1cfb',
                    'CDT_System Project'::'CDT_System'::'Operational Analysis'::'Operational Entities'::'Trainer'.'89f8a6ce-750e-4fe4-92ad-9085f4a8c50b',
                    'CDT_System Project'::'CDT_System'::'Operational Analysis'::'Operational Entities'::'Trainer'.'2449e927-0200-41df-bb5e-18d3830321ba',
                    'CDT_System Project'::'CDT_System'::'Operational Analysis'::'Operational Entities'::'Trainer'.'809b5c3b-80d8-43e4-bba8-39ba3be8e76c'); 
                }  
                part 'Parent' : Entity  { 
                    attribute :>> isAbstract = false; 
                    attribute :>> isActor = true; 
                    attribute :>> isHuman = true; 
                    allocation 'b927469a-2e80-4092-8091-a7aba1627b76' : ComponentFunctionalAllocation
                        allocate function ::> 'CDT_System Project'::'CDT_System'::'Operational Analysis'::'Operational Activities'::'Root Operational Activity'.'Report received'
                        to component ::> 'CDT_System Project'::'CDT_System'::'Operational Analysis'::'Operational Entities'::'Parent';
                    perform 'CDT_System Project'::'CDT_System'::'Operational Analysis'::'Operational Activities'::'Root Operational Activity'.'Report received' ; 
                    ref :>> ownedFunctionalAllocation =  ('CDT_System Project'::'CDT_System'::'Operational Analysis'::'Operational Entities'::'Parent'.'b927469a-2e80-4092-8091-a7aba1627b76'); 
                }  
                part 'Athlete' : Entity  { 
                    attribute :>> isAbstract = false; 
                    attribute :>> isActor = true; 
                    attribute :>> isHuman = true; 
                    allocation '96b381d8-cf64-4e1c-84c6-53532d8ae8f1' : ComponentFunctionalAllocation
                        allocate function ::> 'CDT_System Project'::'CDT_System'::'Operational Analysis'::'Operational Activities'::'Root Operational Activity'.'Provide Data for Profile'
                        to component ::> 'CDT_System Project'::'CDT_System'::'Operational Analysis'::'Operational Entities'::'Athlete';
                    perform 'CDT_System Project'::'CDT_System'::'Operational Analysis'::'Operational Activities'::'Root Operational Activity'.'Provide Data for Profile' ; 
                    allocation '5a4d78f5-27bf-4364-a549-2bf2fdc948f6' : ComponentFunctionalAllocation
                        allocate function ::> 'CDT_System Project'::'CDT_System'::'Operational Analysis'::'Operational Activities'::'Root Operational Activity'.'Recieve ID'
                        to component ::> 'CDT_System Project'::'CDT_System'::'Operational Analysis'::'Operational Entities'::'Athlete';
                    perform 'CDT_System Project'::'CDT_System'::'Operational Analysis'::'Operational Activities'::'Root Operational Activity'.'Recieve ID' ; 
                    allocation 'c0d7519d-bd06-4a79-9089-d1169a694194' : ComponentFunctionalAllocation
                        allocate function ::> 'CDT_System Project'::'CDT_System'::'Operational Analysis'::'Operational Activities'::'Root Operational Activity'.'Insert ID into Sensing Device'
                        to component ::> 'CDT_System Project'::'CDT_System'::'Operational Analysis'::'Operational Entities'::'Athlete';
                    perform 'CDT_System Project'::'CDT_System'::'Operational Analysis'::'Operational Activities'::'Root Operational Activity'.'Insert ID into Sensing Device' ; 
                    allocation '194df74d-e52f-42b0-abd1-9f767cfe8682' : ComponentFunctionalAllocation
                        allocate function ::> 'CDT_System Project'::'CDT_System'::'Operational Analysis'::'Operational Activities'::'Root Operational Activity'.'Place on Helmut'
                        to component ::> 'CDT_System Project'::'CDT_System'::'Operational Analysis'::'Operational Entities'::'Athlete';
                    perform 'CDT_System Project'::'CDT_System'::'Operational Analysis'::'Operational Activities'::'Root Operational Activity'.'Place on Helmut' ; 
                    allocation '34d48850-0d35-42e9-8f27-2a6e051b1c63' : ComponentFunctionalAllocation
                        allocate function ::> 'CDT_System Project'::'CDT_System'::'Operational Analysis'::'Operational Activities'::'Root Operational Activity'.'Athlete Particpates in Activity'
                        to component ::> 'CDT_System Project'::'CDT_System'::'Operational Analysis'::'Operational Entities'::'Athlete';
                    perform 'CDT_System Project'::'CDT_System'::'Operational Analysis'::'Operational Activities'::'Root Operational Activity'.'Athlete Particpates in Activity' ; 
                    allocation 'ae10e5d9-9243-4774-8594-c1f462a2d142' : ComponentFunctionalAllocation
                        allocate function ::> 'CDT_System Project'::'CDT_System'::'Operational Analysis'::'Operational Activities'::'Root Operational Activity'.'Yield to Evaluation'
                        to component ::> 'CDT_System Project'::'CDT_System'::'Operational Analysis'::'Operational Entities'::'Athlete';
                    perform 'CDT_System Project'::'CDT_System'::'Operational Analysis'::'Operational Activities'::'Root Operational Activity'.'Yield to Evaluation' ; 
                    allocation 'b4cbf59e-b562-42fd-8a60-ef50afa576bf' : ComponentFunctionalAllocation
                        allocate function ::> 'CDT_System Project'::'CDT_System'::'Operational Analysis'::'Operational Activities'::'Root Operational Activity'.'Report Received'
                        to component ::> 'CDT_System Project'::'CDT_System'::'Operational Analysis'::'Operational Entities'::'Athlete';
                    perform 'CDT_System Project'::'CDT_System'::'Operational Analysis'::'Operational Activities'::'Root Operational Activity'.'Report Received' ; 
                    ref :>> ownedFunctionalAllocation =  ('CDT_System Project'::'CDT_System'::'Operational Analysis'::'Operational Entities'::'Athlete'.'96b381d8-cf64-4e1c-84c6-53532d8ae8f1',
                    'CDT_System Project'::'CDT_System'::'Operational Analysis'::'Operational Entities'::'Athlete'.'5a4d78f5-27bf-4364-a549-2bf2fdc948f6',
                    'CDT_System Project'::'CDT_System'::'Operational Analysis'::'Operational Entities'::'Athlete'.'c0d7519d-bd06-4a79-9089-d1169a694194',
                    'CDT_System Project'::'CDT_System'::'Operational Analysis'::'Operational Entities'::'Athlete'.'194df74d-e52f-42b0-abd1-9f767cfe8682',
                    'CDT_System Project'::'CDT_System'::'Operational Analysis'::'Operational Entities'::'Athlete'.'34d48850-0d35-42e9-8f27-2a6e051b1c63',
                    'CDT_System Project'::'CDT_System'::'Operational Analysis'::'Operational Entities'::'Athlete'.'ae10e5d9-9243-4774-8594-c1f462a2d142',
                    'CDT_System Project'::'CDT_System'::'Operational Analysis'::'Operational Entities'::'Athlete'.'b4cbf59e-b562-42fd-8a60-ef50afa576bf'); 
                }  
                part 'Instituion' : Entity  { 
                    attribute :>> isAbstract = false; 
                    attribute :>> isActor = true; 
                    attribute :>> isHuman = true; 
                    allocation '45c38267-6bb6-4fe3-b101-f715d652e59a' : ComponentFunctionalAllocation
                        allocate function ::> 'CDT_System Project'::'CDT_System'::'Operational Analysis'::'Operational Activities'::'Root Operational Activity'.'Aquire System'
                        to component ::> 'CDT_System Project'::'CDT_System'::'Operational Analysis'::'Operational Entities'::'Instituion';
                    perform 'CDT_System Project'::'CDT_System'::'Operational Analysis'::'Operational Activities'::'Root Operational Activity'.'Aquire System' ; 
                    allocation '400e5805-6164-4c0a-b6a9-59a528220158' : ComponentFunctionalAllocation
                        allocate function ::> 'CDT_System Project'::'CDT_System'::'Operational Analysis'::'Operational Activities'::'Root Operational Activity'.'Report Received'
                        to component ::> 'CDT_System Project'::'CDT_System'::'Operational Analysis'::'Operational Entities'::'Instituion';
                    perform 'CDT_System Project'::'CDT_System'::'Operational Analysis'::'Operational Activities'::'Root Operational Activity'.'Report Received' ; 
                    allocation '18e7e9bc-9c97-4f06-b459-6b4ca641a0f9' : ComponentFunctionalAllocation
                        allocate function ::> 'CDT_System Project'::'CDT_System'::'Operational Analysis'::'Operational Activities'::'Root Operational Activity'.'Established Concussion Policy'
                        to component ::> 'CDT_System Project'::'CDT_System'::'Operational Analysis'::'Operational Entities'::'Instituion';
                    perform 'CDT_System Project'::'CDT_System'::'Operational Analysis'::'Operational Activities'::'Root Operational Activity'.'Established Concussion Policy' ; 
                    ref :>> ownedFunctionalAllocation =  ('CDT_System Project'::'CDT_System'::'Operational Analysis'::'Operational Entities'::'Instituion'.'45c38267-6bb6-4fe3-b101-f715d652e59a',
                    'CDT_System Project'::'CDT_System'::'Operational Analysis'::'Operational Entities'::'Instituion'.'400e5805-6164-4c0a-b6a9-59a528220158',
                    'CDT_System Project'::'CDT_System'::'Operational Analysis'::'Operational Entities'::'Instituion'.'18e7e9bc-9c97-4f06-b459-6b4ca641a0f9'); 
                }  
                part 'Secure Cloud' : Entity  { 
                    attribute :>> isAbstract = false; 
                    attribute :>> isActor = false; 
                    attribute :>> isHuman = false; 
                    allocation '406b02ef-b4fc-424e-80fd-14455acfeae7' : ComponentFunctionalAllocation
                        allocate function ::> 'CDT_System Project'::'CDT_System'::'Operational Analysis'::'Operational Activities'::'Root Operational Activity'.'Store Profile'
                        to component ::> 'CDT_System Project'::'CDT_System'::'Operational Analysis'::'Operational Entities'::'Secure Cloud';
                    perform 'CDT_System Project'::'CDT_System'::'Operational Analysis'::'Operational Activities'::'Root Operational Activity'.'Store Profile' ; 
                    allocation 'c51382eb-3ccf-4dc5-81d0-7801391069c3' : ComponentFunctionalAllocation
                        allocate function ::> 'CDT_System Project'::'CDT_System'::'Operational Analysis'::'Operational Activities'::'Root Operational Activity'.'Data stored'
                        to component ::> 'CDT_System Project'::'CDT_System'::'Operational Analysis'::'Operational Entities'::'Secure Cloud';
                    perform 'CDT_System Project'::'CDT_System'::'Operational Analysis'::'Operational Activities'::'Root Operational Activity'.'Data stored' ; 
                    allocation 'e056ed73-020f-48da-b06a-32e5ae6c7a4e' : ComponentFunctionalAllocation
                        allocate function ::> 'CDT_System Project'::'CDT_System'::'Operational Analysis'::'Operational Activities'::'Root Operational Activity'.'Generates Reports'
                        to component ::> 'CDT_System Project'::'CDT_System'::'Operational Analysis'::'Operational Entities'::'Secure Cloud';
                    perform 'CDT_System Project'::'CDT_System'::'Operational Analysis'::'Operational Activities'::'Root Operational Activity'.'Generates Reports' ; 
                    ref :>> ownedFunctionalAllocation =  ('CDT_System Project'::'CDT_System'::'Operational Analysis'::'Operational Entities'::'Secure Cloud'.'406b02ef-b4fc-424e-80fd-14455acfeae7',
                    'CDT_System Project'::'CDT_System'::'Operational Analysis'::'Operational Entities'::'Secure Cloud'.'c51382eb-3ccf-4dc5-81d0-7801391069c3',
                    'CDT_System Project'::'CDT_System'::'Operational Analysis'::'Operational Entities'::'Secure Cloud'.'e056ed73-020f-48da-b06a-32e5ae6c7a4e'); 
                }  
                part 'ID Device' : Entity  { 
                    attribute :>> isAbstract = false; 
                    attribute :>> isActor = false; 
                    attribute :>> isHuman = false; 
                    allocation '8e0877dc-2299-4542-8d51-95a5a49b975b' : ComponentFunctionalAllocation
                        allocate function ::> 'CDT_System Project'::'CDT_System'::'Operational Analysis'::'Operational Activities'::'Root Operational Activity'.'Create Unique IDs for Athlete'
                        to component ::> 'CDT_System Project'::'CDT_System'::'Operational Analysis'::'Operational Entities'::'ID Device';
                    perform 'CDT_System Project'::'CDT_System'::'Operational Analysis'::'Operational Activities'::'Root Operational Activity'.'Create Unique IDs for Athlete' ; 
                    allocation '688b9405-6121-495c-9509-38e3b3465f3e' : ComponentFunctionalAllocation
                        allocate function ::> 'CDT_System Project'::'CDT_System'::'Operational Analysis'::'Operational Activities'::'Root Operational Activity'.'Provide ID Information'
                        to component ::> 'CDT_System Project'::'CDT_System'::'Operational Analysis'::'Operational Entities'::'ID Device';
                    perform 'CDT_System Project'::'CDT_System'::'Operational Analysis'::'Operational Activities'::'Root Operational Activity'.'Provide ID Information' ; 
                    allocation '11381e9f-0d3a-41b8-87dc-b555ef15533e' : ComponentFunctionalAllocation
                        allocate function ::> 'CDT_System Project'::'CDT_System'::'Operational Analysis'::'Operational Activities'::'Root Operational Activity'.'Device'
                        to component ::> 'CDT_System Project'::'CDT_System'::'Operational Analysis'::'Operational Entities'::'ID Device';
                    perform 'CDT_System Project'::'CDT_System'::'Operational Analysis'::'Operational Activities'::'Root Operational Activity'.'Device' ; 
                    ref :>> ownedFunctionalAllocation =  ('CDT_System Project'::'CDT_System'::'Operational Analysis'::'Operational Entities'::'ID Device'.'8e0877dc-2299-4542-8d51-95a5a49b975b',
                    'CDT_System Project'::'CDT_System'::'Operational Analysis'::'Operational Entities'::'ID Device'.'688b9405-6121-495c-9509-38e3b3465f3e',
                    'CDT_System Project'::'CDT_System'::'Operational Analysis'::'Operational Entities'::'ID Device'.'11381e9f-0d3a-41b8-87dc-b555ef15533e'); 
                }  
                part 'Helmet' : Entity  { 
                    attribute :>> isAbstract = false; 
                    attribute :>> isActor = false; 
                    attribute :>> isHuman = false; 
                    allocation '3aecadb3-07fe-419e-a716-dc142540c085' : ComponentFunctionalAllocation
                        allocate function ::> 'CDT_System Project'::'CDT_System'::'Operational Analysis'::'Operational Activities'::'Root Operational Activity'.'Provide access to sensing device mounting'
                        to component ::> 'CDT_System Project'::'CDT_System'::'Operational Analysis'::'Operational Entities'::'Helmet';
                    perform 'CDT_System Project'::'CDT_System'::'Operational Analysis'::'Operational Activities'::'Root Operational Activity'.'Provide access to sensing device mounting' ; 
                    allocation '4b1dc8bd-860a-4eb7-99a4-236dd613517a' : ComponentFunctionalAllocation
                        allocate function ::> 'CDT_System Project'::'CDT_System'::'Operational Analysis'::'Operational Activities'::'Root Operational Activity'.'Receive Athlete '
                        to component ::> 'CDT_System Project'::'CDT_System'::'Operational Analysis'::'Operational Entities'::'Helmet';
                    perform 'CDT_System Project'::'CDT_System'::'Operational Analysis'::'Operational Activities'::'Root Operational Activity'.'Receive Athlete ' ; 
                    allocation 'ec3d506e-2f3c-4c86-8fb7-fb03b17b4b62' : ComponentFunctionalAllocation
                        allocate function ::> 'CDT_System Project'::'CDT_System'::'Operational Analysis'::'Operational Activities'::'Root Operational Activity'.'Helmet Receives a Hit'
                        to component ::> 'CDT_System Project'::'CDT_System'::'Operational Analysis'::'Operational Entities'::'Helmet';
                    perform 'CDT_System Project'::'CDT_System'::'Operational Analysis'::'Operational Activities'::'Root Operational Activity'.'Helmet Receives a Hit' ; 
                    ref :>> ownedFunctionalAllocation =  ('CDT_System Project'::'CDT_System'::'Operational Analysis'::'Operational Entities'::'Helmet'.'3aecadb3-07fe-419e-a716-dc142540c085',
                    'CDT_System Project'::'CDT_System'::'Operational Analysis'::'Operational Entities'::'Helmet'.'4b1dc8bd-860a-4eb7-99a4-236dd613517a',
                    'CDT_System Project'::'CDT_System'::'Operational Analysis'::'Operational Entities'::'Helmet'.'ec3d506e-2f3c-4c86-8fb7-fb03b17b4b62'); 
                }  
                part 'Sensing Device' : Entity  { 
                    attribute :>> isAbstract = false; 
                    attribute :>> isActor = false; 
                    attribute :>> isHuman = false; 
                    allocation 'd9260609-2372-4181-999e-0aee47fd00d2' : ComponentFunctionalAllocation
                        allocate function ::> 'CDT_System Project'::'CDT_System'::'Operational Analysis'::'Operational Activities'::'Root Operational Activity'.'Provide access to helmet mounting'
                        to component ::> 'CDT_System Project'::'CDT_System'::'Operational Analysis'::'Operational Entities'::'Sensing Device';
                    perform 'CDT_System Project'::'CDT_System'::'Operational Analysis'::'Operational Activities'::'Root Operational Activity'.'Provide access to helmet mounting' ; 
                    allocation 'fc501cee-5e11-4c0c-ac21-17c0ae0b70a6' : ComponentFunctionalAllocation
                        allocate function ::> 'CDT_System Project'::'CDT_System'::'Operational Analysis'::'Operational Activities'::'Root Operational Activity'.'Recieve ID'
                        to component ::> 'CDT_System Project'::'CDT_System'::'Operational Analysis'::'Operational Entities'::'Sensing Device';
                    perform 'CDT_System Project'::'CDT_System'::'Operational Analysis'::'Operational Activities'::'Root Operational Activity'.'Recieve ID' ; 
                    allocation '0e88f162-8b51-48c8-8598-6beb746cc287' : ComponentFunctionalAllocation
                        allocate function ::> 'CDT_System Project'::'CDT_System'::'Operational Analysis'::'Operational Activities'::'Root Operational Activity'.'Enable Secure Collection'
                        to component ::> 'CDT_System Project'::'CDT_System'::'Operational Analysis'::'Operational Entities'::'Sensing Device';
                    perform 'CDT_System Project'::'CDT_System'::'Operational Analysis'::'Operational Activities'::'Root Operational Activity'.'Enable Secure Collection' ; 
                    allocation '467d412b-85f0-445b-88b2-a637c8f49a1f' : ComponentFunctionalAllocation
                        allocate function ::> 'CDT_System Project'::'CDT_System'::'Operational Analysis'::'Operational Activities'::'Root Operational Activity'.'Enable Monitoring'
                        to component ::> 'CDT_System Project'::'CDT_System'::'Operational Analysis'::'Operational Entities'::'Sensing Device';
                    perform 'CDT_System Project'::'CDT_System'::'Operational Analysis'::'Operational Activities'::'Root Operational Activity'.'Enable Monitoring' ; 
                    allocation 'c36b7f88-e6a2-4d0e-8a61-947c45985c40' : ComponentFunctionalAllocation
                        allocate function ::> 'CDT_System Project'::'CDT_System'::'Operational Analysis'::'Operational Activities'::'Root Operational Activity'.'Data is Retrieved'
                        to component ::> 'CDT_System Project'::'CDT_System'::'Operational Analysis'::'Operational Entities'::'Sensing Device';
                    perform 'CDT_System Project'::'CDT_System'::'Operational Analysis'::'Operational Activities'::'Root Operational Activity'.'Data is Retrieved' ; 
                    allocation '632e2e2b-8885-4914-9a3f-ed802b0bb139' : ComponentFunctionalAllocation
                        allocate function ::> 'CDT_System Project'::'CDT_System'::'Operational Analysis'::'Operational Activities'::'Root Operational Activity'.'Device records Hit'
                        to component ::> 'CDT_System Project'::'CDT_System'::'Operational Analysis'::'Operational Entities'::'Sensing Device';
                    perform 'CDT_System Project'::'CDT_System'::'Operational Analysis'::'Operational Activities'::'Root Operational Activity'.'Device records Hit' ; 
                    allocation '274d71ed-1b76-4bf3-bd6b-fb068fb65b04' : ComponentFunctionalAllocation
                        allocate function ::> 'CDT_System Project'::'CDT_System'::'Operational Analysis'::'Operational Activities'::'Root Operational Activity'.'Device alerts possible Concussion'
                        to component ::> 'CDT_System Project'::'CDT_System'::'Operational Analysis'::'Operational Entities'::'Sensing Device';
                    perform 'CDT_System Project'::'CDT_System'::'Operational Analysis'::'Operational Activities'::'Root Operational Activity'.'Device alerts possible Concussion' ; 
                    state 'StateMachine 1' : StateMachine  { 
                        attribute :>> isControlOperator = false; 
                        state 'Off' : Mode;  
                        state 'ON' : Mode { 
                            state 'ID Checking' : Mode;  
                            state 'IID Detected' : Mode { 
                                ref :>> doActivity =  ('CDT_System Project'::'CDT_System'::'Operational Analysis'::'Operational Activities'::'Root Operational Activity'.'Device records Hit',
                                'CDT_System Project'::'CDT_System'::'Operational Analysis'::'Operational Activities'::'Root Operational Activity'.'Device alerts possible Concussion',
                                'CDT_System Project'::'CDT_System'::'Operational Analysis'::'Operational Activities'::'Root Operational Activity'.'Data is Retrieved'); 
                                ref :>> entry =  ('CDT_System Project'::'CDT_System'::'Operational Analysis'::'Operational Activities'::'Root Operational Activity'.'Enable Secure Collection',
                                'CDT_System Project'::'CDT_System'::'Operational Analysis'::'Operational Activities'::'Root Operational Activity'.'Enable Monitoring'); 
                            }  
                            entry; then 'ID Checking';  
                            transition '584ae3b1-c6c4-4562-a248-8e964b231aa7' 
                                first 'CDT_System Project'::'CDT_System'::'Operational Analysis'::'Operational Entities'::'Sensing Device'.'StateMachine 1'.'ON'.'ID Checking'
                                accept 'Athlete ID' :> 'CDT_System Project'::'CDT_System'::'Operational Analysis'::'Data'::'Athlete ID'
                                then 'CDT_System Project'::'CDT_System'::'Operational Analysis'::'Operational Entities'::'Sensing Device'.'StateMachine 1'.'ON'.'IID Detected' {
                            }  
                            ref :>> referencedStates =  ('CDT_System Project'::'CDT_System'::'Operational Analysis'::'Operational Entities'::'Sensing Device'.'StateMachine 1'.'ON'.'ID Checking',
                            'CDT_System Project'::'CDT_System'::'Operational Analysis'::'Operational Entities'::'Sensing Device'.'StateMachine 1'.'ON'.'IID Detected'); 
                        }  
                        transition '643fd0b5-9c10-4731-a35a-786146c37ca3' 
                            first 'CDT_System Project'::'CDT_System'::'Operational Analysis'::'Operational Entities'::'Sensing Device'.'StateMachine 1'.'Off'
                            accept 'Power Applied' :> 'CDT_System Project'::'CDT_System'::'Operational Analysis'::'Data'::'Power Applied'
                            then 'CDT_System Project'::'CDT_System'::'Operational Analysis'::'Operational Entities'::'Sensing Device'.'StateMachine 1'.'ON' {
                        }  
                        entry; then 'Off';  
                    }  
                    ref :>> ownedFunctionalAllocation =  ('CDT_System Project'::'CDT_System'::'Operational Analysis'::'Operational Entities'::'Sensing Device'.'d9260609-2372-4181-999e-0aee47fd00d2',
                    'CDT_System Project'::'CDT_System'::'Operational Analysis'::'Operational Entities'::'Sensing Device'.'fc501cee-5e11-4c0c-ac21-17c0ae0b70a6',
                    'CDT_System Project'::'CDT_System'::'Operational Analysis'::'Operational Entities'::'Sensing Device'.'0e88f162-8b51-48c8-8598-6beb746cc287',
                    'CDT_System Project'::'CDT_System'::'Operational Analysis'::'Operational Entities'::'Sensing Device'.'467d412b-85f0-445b-88b2-a637c8f49a1f',
                    'CDT_System Project'::'CDT_System'::'Operational Analysis'::'Operational Entities'::'Sensing Device'.'c36b7f88-e6a2-4d0e-8a61-947c45985c40',
                    'CDT_System Project'::'CDT_System'::'Operational Analysis'::'Operational Entities'::'Sensing Device'.'632e2e2b-8885-4914-9a3f-ed802b0bb139',
                    'CDT_System Project'::'CDT_System'::'Operational Analysis'::'Operational Entities'::'Sensing Device'.'274d71ed-1b76-4bf3-bd6b-fb068fb65b04'); 
                    ref :>> ownedStateMachines =  ('CDT_System Project'::'CDT_System'::'Operational Analysis'::'Operational Entities'::'Sensing Device'.'StateMachine 1'); 
                }  
            } 
            package  'Operational Activities' {
                @PackageMeta {
                    type = "OperationalActivityPkg";
                } 
                action 'Root Operational Activity' : OperationalActivity  { 
                    attribute :>> isDerived = false; 
                    attribute :>> aggregationKind = AggregationKind::UNSET; 
                    attribute :>> isFinal = false; 
                    attribute :>> isPartOfKey = false; 
                    attribute :>> kind = FunctionKind::FUNCTION; 
                    attribute :>> isMaxInclusive = false; 
                    attribute :>> isUnique = false; 
                    attribute :>> isReadOnly = false; 
                    attribute :>> isMinInclusive = false; 
                    attribute :>> isStatic = false; 
                    attribute :>> isOrdered = false; 
                    attribute :>> isAbstract = false; 
                    action 'Acquire Device' : OperationalProcess  { 
                        attribute :>> kind = FunctionalChainKind::SIMPLE; 
                        connection '1d2781f8-17d2-48e9-a477-d03adc87b0f3' : FunctionalChainInvolvementLink 
                            connect source ::> 'CDT_System Project'::'CDT_System'::'Operational Analysis'::'Operational Activities'::'Root Operational Activity'.'Acquire Device'.'c858e015-892e-4207-a3dc-957c3ec6a967'
                            to  target ::> 'CDT_System Project'::'CDT_System'::'Operational Analysis'::'Operational Activities'::'Root Operational Activity'.'Acquire Device'.'76a694aa-b1f6-4e93-a93f-154cc26c7d18' {

                                ref :>> involved = 'CDT_System Project'::'CDT_System'::'Operational Analysis'::'Operational Activities'::'Root Operational Activity'.'8aa3c385-d166-42b6-8aa7-42fb00b348dd';

                            } 
                        ref action '76a694aa-b1f6-4e93-a93f-154cc26c7d18' = 'CDT_System Project'::'CDT_System'::'Operational Analysis'::'Operational Activities'::'Root Operational Activity'.'Create profiles for Athletes'; 
                        ref action 'c858e015-892e-4207-a3dc-957c3ec6a967' = 'CDT_System Project'::'CDT_System'::'Operational Analysis'::'Operational Activities'::'Root Operational Activity'.'Provide Data for Profile'; 
                        connection 'f2069f0b-e350-496e-a755-3082f47979bf' : FunctionalChainInvolvementLink 
                            connect source ::> 'CDT_System Project'::'CDT_System'::'Operational Analysis'::'Operational Activities'::'Root Operational Activity'.'Acquire Device'.'6166c4b3-06f2-4cea-9d8f-cb2a82b84b6f'
                            to  target ::> 'CDT_System Project'::'CDT_System'::'Operational Analysis'::'Operational Activities'::'Root Operational Activity'.'Acquire Device'.'76a694aa-b1f6-4e93-a93f-154cc26c7d18' {

                                ref :>> involved = 'CDT_System Project'::'CDT_System'::'Operational Analysis'::'Operational Activities'::'Root Operational Activity'.'cc920cd2-9f5a-4453-b358-341dcd2a252b';

                            } 
                        ref action '6166c4b3-06f2-4cea-9d8f-cb2a82b84b6f' = 'CDT_System Project'::'CDT_System'::'Operational Analysis'::'Operational Activities'::'Root Operational Activity'.'Aquire System'; 
                        connection '197bd8c6-84c3-4efc-bcde-684d80a897aa' : FunctionalChainInvolvementLink 
                            connect source ::> 'CDT_System Project'::'CDT_System'::'Operational Analysis'::'Operational Activities'::'Root Operational Activity'.'Acquire Device'.'76a694aa-b1f6-4e93-a93f-154cc26c7d18'
                            to  target ::> 'CDT_System Project'::'CDT_System'::'Operational Analysis'::'Operational Activities'::'Root Operational Activity'.'Acquire Device'.'505022b4-f0e9-4366-b1cd-210f6a9bec3b' {

                                ref :>> involved = 'CDT_System Project'::'CDT_System'::'Operational Analysis'::'Operational Activities'::'Root Operational Activity'.'b3bed4c5-e260-48f0-bfbe-f8e400986465';

                            } 
                        ref action '505022b4-f0e9-4366-b1cd-210f6a9bec3b' = 'CDT_System Project'::'CDT_System'::'Operational Analysis'::'Operational Activities'::'Root Operational Activity'.'Store Profile'; 
                        ref action 'f0958e58-16ef-4ece-b6d7-346b050f1994' = 'CDT_System Project'::'CDT_System'::'Operational Analysis'::'Operational Activities'::'Root Operational Activity'.'Create Unique IDs'; 
                        connection '6dcc3e14-4398-459b-be9f-5c0c3131f565' : FunctionalChainInvolvementLink 
                            connect source ::> 'CDT_System Project'::'CDT_System'::'Operational Analysis'::'Operational Activities'::'Root Operational Activity'.'Acquire Device'.'76a694aa-b1f6-4e93-a93f-154cc26c7d18'
                            to  target ::> 'CDT_System Project'::'CDT_System'::'Operational Analysis'::'Operational Activities'::'Root Operational Activity'.'Acquire Device'.'f0958e58-16ef-4ece-b6d7-346b050f1994' {

                                ref :>> involved = 'CDT_System Project'::'CDT_System'::'Operational Analysis'::'Operational Activities'::'Root Operational Activity'.'96cd2019-7155-4e26-9482-b59e3d887b05';

                            } 
                        ref action 'e66ef116-0b0c-4233-87b1-318265a673f1' = 'CDT_System Project'::'CDT_System'::'Operational Analysis'::'Operational Activities'::'Root Operational Activity'.'Create Unique IDs for Athlete'; 
                        connection 'e669443b-ebfb-40d9-b4d8-c5a035b849e5' : FunctionalChainInvolvementLink 
                            connect source ::> 'CDT_System Project'::'CDT_System'::'Operational Analysis'::'Operational Activities'::'Root Operational Activity'.'Acquire Device'.'f0958e58-16ef-4ece-b6d7-346b050f1994'
                            to  target ::> 'CDT_System Project'::'CDT_System'::'Operational Analysis'::'Operational Activities'::'Root Operational Activity'.'Acquire Device'.'e66ef116-0b0c-4233-87b1-318265a673f1' {

                                ref :>> involved = 'CDT_System Project'::'CDT_System'::'Operational Analysis'::'Operational Activities'::'Root Operational Activity'.'b4b1baea-ff21-4412-be81-677404a3aff8';

                            } 
                        ref action 'bd2ddd45-db27-4184-bda8-0d69c7ceff8c' = 'CDT_System Project'::'CDT_System'::'Operational Analysis'::'Operational Activities'::'Root Operational Activity'.'Provide ID to Athlete'; 
                        connection '9765c48a-d7cf-4c08-a865-e7a67d5a206a' : FunctionalChainInvolvementLink 
                            connect source ::> 'CDT_System Project'::'CDT_System'::'Operational Analysis'::'Operational Activities'::'Root Operational Activity'.'Acquire Device'.'e66ef116-0b0c-4233-87b1-318265a673f1'
                            to  target ::> 'CDT_System Project'::'CDT_System'::'Operational Analysis'::'Operational Activities'::'Root Operational Activity'.'Acquire Device'.'bd2ddd45-db27-4184-bda8-0d69c7ceff8c' {

                                ref :>> involved = 'CDT_System Project'::'CDT_System'::'Operational Analysis'::'Operational Activities'::'Root Operational Activity'.'43ebd273-9008-4d4a-bbbe-c0a6fa954cc6';

                            } 
                        ref action '45ed0a79-de25-4323-8380-87c6fe891a9f' = 'CDT_System Project'::'CDT_System'::'Operational Analysis'::'Operational Activities'::'Root Operational Activity'.'Recieve ID'; 
                        connection '3096a778-89b4-42c9-91ee-5800b22fd0ea' : FunctionalChainInvolvementLink 
                            connect source ::> 'CDT_System Project'::'CDT_System'::'Operational Analysis'::'Operational Activities'::'Root Operational Activity'.'Acquire Device'.'bd2ddd45-db27-4184-bda8-0d69c7ceff8c'
                            to  target ::> 'CDT_System Project'::'CDT_System'::'Operational Analysis'::'Operational Activities'::'Root Operational Activity'.'Acquire Device'.'45ed0a79-de25-4323-8380-87c6fe891a9f' {

                                ref :>> involved = 'CDT_System Project'::'CDT_System'::'Operational Analysis'::'Operational Activities'::'Root Operational Activity'.'f8c5c195-2105-4cfc-b95f-c2a47986f8ed';

                            } 
                    }  
                    action 'Maintain' : OperationalProcess  { 
                        attribute :>> kind = FunctionalChainKind::SIMPLE; 
                        connection '4b13d0f3-0b79-49cd-9185-cc433697230c' : FunctionalChainInvolvementLink 
                            connect source ::> 'CDT_System Project'::'CDT_System'::'Operational Analysis'::'Operational Activities'::'Root Operational Activity'.'Maintain'.'be9355db-9a9b-4999-b694-f79cba5afecf'
                            to  target ::> 'CDT_System Project'::'CDT_System'::'Operational Analysis'::'Operational Activities'::'Root Operational Activity'.'Maintain'.'5f6d7e52-61b1-4fb3-b28a-ca250c17f2f7' {

                                ref :>> involved = 'CDT_System Project'::'CDT_System'::'Operational Analysis'::'Operational Activities'::'Root Operational Activity'.'a58925f4-2c77-4d13-a5a8-ab0774fcf3e6';

                            } 
                        ref action '5f6d7e52-61b1-4fb3-b28a-ca250c17f2f7' = 'CDT_System Project'::'CDT_System'::'Operational Analysis'::'Operational Activities'::'Root Operational Activity'.'Assemble System Components'; 
                        ref action 'be9355db-9a9b-4999-b694-f79cba5afecf' = 'CDT_System Project'::'CDT_System'::'Operational Analysis'::'Operational Activities'::'Root Operational Activity'.'Aquire System'; 
                        connection '6f4fb2f3-a2ce-437a-9678-4201abeea5b2' : FunctionalChainInvolvementLink 
                            connect source ::> 'CDT_System Project'::'CDT_System'::'Operational Analysis'::'Operational Activities'::'Root Operational Activity'.'Maintain'.'dacf9d1c-3a24-49d1-8fe4-ca2bbfecfdb7'
                            to  target ::> 'CDT_System Project'::'CDT_System'::'Operational Analysis'::'Operational Activities'::'Root Operational Activity'.'Maintain'.'5f6d7e52-61b1-4fb3-b28a-ca250c17f2f7' {

                                ref :>> involved = 'CDT_System Project'::'CDT_System'::'Operational Analysis'::'Operational Activities'::'Root Operational Activity'.'a67bdeeb-5438-494e-b4c8-5566a801ffa9';

                            } 
                        ref action 'dacf9d1c-3a24-49d1-8fe4-ca2bbfecfdb7' = 'CDT_System Project'::'CDT_System'::'Operational Analysis'::'Operational Activities'::'Root Operational Activity'.'Provide access to helmet mounting'; 
                        connection '8014c80c-ad24-4498-af34-20b452d2da6e' : FunctionalChainInvolvementLink 
                            connect source ::> 'CDT_System Project'::'CDT_System'::'Operational Analysis'::'Operational Activities'::'Root Operational Activity'.'Maintain'.'a58544d2-26b4-4dcd-a3de-a355f600993c'
                            to  target ::> 'CDT_System Project'::'CDT_System'::'Operational Analysis'::'Operational Activities'::'Root Operational Activity'.'Maintain'.'5f6d7e52-61b1-4fb3-b28a-ca250c17f2f7' {

                                ref :>> involved = 'CDT_System Project'::'CDT_System'::'Operational Analysis'::'Operational Activities'::'Root Operational Activity'.'8536e8a8-d249-4f41-8ae0-a99b8f0f2bac';

                            } 
                        ref action 'a58544d2-26b4-4dcd-a3de-a355f600993c' = 'CDT_System Project'::'CDT_System'::'Operational Analysis'::'Operational Activities'::'Root Operational Activity'.'Provide access to sensing device mounting'; 
                        connection 'd68288d0-04e4-4b36-90bc-0e126fb6fcb7' : FunctionalChainInvolvementLink 
                            connect source ::> 'CDT_System Project'::'CDT_System'::'Operational Analysis'::'Operational Activities'::'Root Operational Activity'.'Maintain'.'5f6d7e52-61b1-4fb3-b28a-ca250c17f2f7'
                            to  target ::> 'CDT_System Project'::'CDT_System'::'Operational Analysis'::'Operational Activities'::'Root Operational Activity'.'Maintain'.'ee7ca695-d2ba-49f2-99a4-60e444f2829c' {

                                ref :>> involved = 'CDT_System Project'::'CDT_System'::'Operational Analysis'::'Operational Activities'::'Root Operational Activity'.'478e664f-6d60-4169-bda0-13ca1ce73db5';

                            } 
                        ref action 'ee7ca695-d2ba-49f2-99a4-60e444f2829c' = 'CDT_System Project'::'CDT_System'::'Operational Analysis'::'Operational Activities'::'Root Operational Activity'.'Prep the device for use'; 
                    }  
                    action 'Activate Detection Device' : OperationalProcess  { 
                        attribute :>> kind = FunctionalChainKind::SIMPLE; 
                        connection 'cc5680a0-2ab7-413d-95cd-d4d98ab38006' : FunctionalChainInvolvementLink 
                            connect source ::> 'CDT_System Project'::'CDT_System'::'Operational Analysis'::'Operational Activities'::'Root Operational Activity'.'Activate Detection Device'.'75b4f3d1-c87a-45b2-80fb-028e66b2eddb'
                            to  target ::> 'CDT_System Project'::'CDT_System'::'Operational Analysis'::'Operational Activities'::'Root Operational Activity'.'Activate Detection Device'.'c892b49b-d813-4a75-a46d-d60e5621b522' {

                                ref :>> involved = 'CDT_System Project'::'CDT_System'::'Operational Analysis'::'Operational Activities'::'Root Operational Activity'.'6ae929bd-82fc-49f5-a5d0-e7f201978207';

                            } 
                        ref action 'c892b49b-d813-4a75-a46d-d60e5621b522' = 'CDT_System Project'::'CDT_System'::'Operational Analysis'::'Operational Activities'::'Root Operational Activity'.'Insert ID into Sensing Device'; 
                        ref action '75b4f3d1-c87a-45b2-80fb-028e66b2eddb' = 'CDT_System Project'::'CDT_System'::'Operational Analysis'::'Operational Activities'::'Root Operational Activity'.'Recieve ID'; 
                        connection '26ae44b9-048a-40e6-9c24-fbbb938b764e' : FunctionalChainInvolvementLink 
                            connect source ::> 'CDT_System Project'::'CDT_System'::'Operational Analysis'::'Operational Activities'::'Root Operational Activity'.'Activate Detection Device'.'c892b49b-d813-4a75-a46d-d60e5621b522'
                            to  target ::> 'CDT_System Project'::'CDT_System'::'Operational Analysis'::'Operational Activities'::'Root Operational Activity'.'Activate Detection Device'.'5d13e115-8fe0-4549-9331-103f4f1f2cb1' {

                                ref :>> involved = 'CDT_System Project'::'CDT_System'::'Operational Analysis'::'Operational Activities'::'Root Operational Activity'.'8692c5e2-7f99-4997-9988-3f6afa1e7099';

                            } 
                        ref action '5d13e115-8fe0-4549-9331-103f4f1f2cb1' = 'CDT_System Project'::'CDT_System'::'Operational Analysis'::'Operational Activities'::'Root Operational Activity'.'Recieve ID'; 
                        connection '9022636b-80c3-43f3-9322-7203a50563c5' : FunctionalChainInvolvementLink 
                            connect source ::> 'CDT_System Project'::'CDT_System'::'Operational Analysis'::'Operational Activities'::'Root Operational Activity'.'Activate Detection Device'.'c892b49b-d813-4a75-a46d-d60e5621b522'
                            to  target ::> 'CDT_System Project'::'CDT_System'::'Operational Analysis'::'Operational Activities'::'Root Operational Activity'.'Activate Detection Device'.'85b6ecc0-9f5d-477e-a96f-dde7a3d676bd' {

                                ref :>> involved = 'CDT_System Project'::'CDT_System'::'Operational Analysis'::'Operational Activities'::'Root Operational Activity'.'675e0c82-d4c3-4978-b1e5-074e665f8324';

                            } 
                        ref action '85b6ecc0-9f5d-477e-a96f-dde7a3d676bd' = 'CDT_System Project'::'CDT_System'::'Operational Analysis'::'Operational Activities'::'Root Operational Activity'.'Place on Helmut'; 
                        connection '8b7c6ec7-7267-44e7-8e54-e20357c9447e' : FunctionalChainInvolvementLink 
                            connect source ::> 'CDT_System Project'::'CDT_System'::'Operational Analysis'::'Operational Activities'::'Root Operational Activity'.'Activate Detection Device'.'5d13e115-8fe0-4549-9331-103f4f1f2cb1'
                            to  target ::> 'CDT_System Project'::'CDT_System'::'Operational Analysis'::'Operational Activities'::'Root Operational Activity'.'Activate Detection Device'.'763c6ce1-537c-4450-8f60-3b5854a6a3db' {

                                ref :>> involved = 'CDT_System Project'::'CDT_System'::'Operational Analysis'::'Operational Activities'::'Root Operational Activity'.'67a031db-38ff-43b0-929a-aeae5ce7c739';

                            } 
                        ref action '763c6ce1-537c-4450-8f60-3b5854a6a3db' = 'CDT_System Project'::'CDT_System'::'Operational Analysis'::'Operational Activities'::'Root Operational Activity'.'Enable Secure Collection'; 
                        connection '8b03c175-dc42-4d35-8e4c-3ebb26d74984' : FunctionalChainInvolvementLink 
                            connect source ::> 'CDT_System Project'::'CDT_System'::'Operational Analysis'::'Operational Activities'::'Root Operational Activity'.'Activate Detection Device'.'763c6ce1-537c-4450-8f60-3b5854a6a3db'
                            to  target ::> 'CDT_System Project'::'CDT_System'::'Operational Analysis'::'Operational Activities'::'Root Operational Activity'.'Activate Detection Device'.'29ff85cc-60cb-4147-b12c-b5fde96913ca' {

                                ref :>> involved = 'CDT_System Project'::'CDT_System'::'Operational Analysis'::'Operational Activities'::'Root Operational Activity'.'847cf44e-6cd6-43b0-8c34-e69ddcea37fb';

                            } 
                        ref action '29ff85cc-60cb-4147-b12c-b5fde96913ca' = 'CDT_System Project'::'CDT_System'::'Operational Analysis'::'Operational Activities'::'Root Operational Activity'.'Enable Monitoring'; 
                        connection '5d726e85-d6dd-40d0-9f02-dbf0e3e6bdf5' : FunctionalChainInvolvementLink 
                            connect source ::> 'CDT_System Project'::'CDT_System'::'Operational Analysis'::'Operational Activities'::'Root Operational Activity'.'Activate Detection Device'.'85b6ecc0-9f5d-477e-a96f-dde7a3d676bd'
                            to  target ::> 'CDT_System Project'::'CDT_System'::'Operational Analysis'::'Operational Activities'::'Root Operational Activity'.'Activate Detection Device'.'cdf3a5e0-328d-4d56-97ac-1103cf12be29' {

                                ref :>> involved = 'CDT_System Project'::'CDT_System'::'Operational Analysis'::'Operational Activities'::'Root Operational Activity'.'8558f31b-5008-4689-b4e7-d6fe30fbcb7e';

                            } 
                        ref action 'cdf3a5e0-328d-4d56-97ac-1103cf12be29' = 'CDT_System Project'::'CDT_System'::'Operational Analysis'::'Operational Activities'::'Root Operational Activity'.'Receive Athlete '; 
                        connection '974c1c4e-b598-4859-a6b6-3d749dc7b11f' : FunctionalChainInvolvementLink 
                            connect source ::> 'CDT_System Project'::'CDT_System'::'Operational Analysis'::'Operational Activities'::'Root Operational Activity'.'Activate Detection Device'.'cdf3a5e0-328d-4d56-97ac-1103cf12be29'
                            to  target ::> 'CDT_System Project'::'CDT_System'::'Operational Analysis'::'Operational Activities'::'Root Operational Activity'.'Activate Detection Device'.'29ff85cc-60cb-4147-b12c-b5fde96913ca' {

                                ref :>> involved = 'CDT_System Project'::'CDT_System'::'Operational Analysis'::'Operational Activities'::'Root Operational Activity'.'dda5962e-7600-48b7-9539-8d8221660ea2';

                            } 
                        ref action 'f503737b-c9bd-4fde-b9e1-9c6a1669affd' = 'CDT_System Project'::'CDT_System'::'Operational Analysis'::'Operational Activities'::'Root Operational Activity'.'Provide ID Information'; 
                        connection 'd2f421de-14d9-4b72-97bc-f63c7fd2fb1a' : FunctionalChainInvolvementLink 
                            connect source ::> 'CDT_System Project'::'CDT_System'::'Operational Analysis'::'Operational Activities'::'Root Operational Activity'.'Activate Detection Device'.'f503737b-c9bd-4fde-b9e1-9c6a1669affd'
                            to  target ::> 'CDT_System Project'::'CDT_System'::'Operational Analysis'::'Operational Activities'::'Root Operational Activity'.'Activate Detection Device'.'763c6ce1-537c-4450-8f60-3b5854a6a3db' {

                                ref :>> involved = 'CDT_System Project'::'CDT_System'::'Operational Analysis'::'Operational Activities'::'Root Operational Activity'.'66c670f2-93c8-4b31-bc85-1625e146fab8';

                            } 
                        ref action '457f1b11-7385-44d2-8afd-e23bf0b6d313' = 'CDT_System Project'::'CDT_System'::'Operational Analysis'::'Operational Activities'::'Root Operational Activity'.'Recieve Enabled Signal from Athelete Helmut'; 
                        connection '6c82b68f-e1c0-4803-a1d2-9f5001a40229' : FunctionalChainInvolvementLink 
                            connect source ::> 'CDT_System Project'::'CDT_System'::'Operational Analysis'::'Operational Activities'::'Root Operational Activity'.'Activate Detection Device'.'29ff85cc-60cb-4147-b12c-b5fde96913ca'
                            to  target ::> 'CDT_System Project'::'CDT_System'::'Operational Analysis'::'Operational Activities'::'Root Operational Activity'.'Activate Detection Device'.'457f1b11-7385-44d2-8afd-e23bf0b6d313' {

                                ref :>> involved = 'CDT_System Project'::'CDT_System'::'Operational Analysis'::'Operational Activities'::'Root Operational Activity'.'ad8be7eb-6edc-42f9-adc8-8d5f8731b545';

                            } 
                    }  
                    action 'Download Data' : OperationalProcess  { 
                        attribute :>> kind = FunctionalChainKind::SIMPLE; 
                        connection '8c7adfdf-70b5-4abf-90be-793bcb87c335' : FunctionalChainInvolvementLink 
                            connect source ::> 'CDT_System Project'::'CDT_System'::'Operational Analysis'::'Operational Activities'::'Root Operational Activity'.'Download Data'.'8eeb2a72-dc25-4845-a13d-127acec19785'
                            to  target ::> 'CDT_System Project'::'CDT_System'::'Operational Analysis'::'Operational Activities'::'Root Operational Activity'.'Download Data'.'e6c20fb4-c655-4dce-a6db-2cc1626c3c62' {

                                ref :>> involved = 'CDT_System Project'::'CDT_System'::'Operational Analysis'::'Operational Activities'::'Root Operational Activity'.'0515a2c6-03ae-4443-b3da-706fd1554f0b';

                            } 
                        ref action 'e6c20fb4-c655-4dce-a6db-2cc1626c3c62' = 'CDT_System Project'::'CDT_System'::'Operational Analysis'::'Operational Activities'::'Root Operational Activity'.'Yield to Evaluation'; 
                        ref action '8eeb2a72-dc25-4845-a13d-127acec19785' = 'CDT_System Project'::'CDT_System'::'Operational Analysis'::'Operational Activities'::'Root Operational Activity'.'Trainer Recieves Concussion Alert'; 
                        connection '32f40710-50b3-4b86-8f17-8ec3fef45522' : FunctionalChainInvolvementLink 
                            connect source ::> 'CDT_System Project'::'CDT_System'::'Operational Analysis'::'Operational Activities'::'Root Operational Activity'.'Download Data'.'e6c20fb4-c655-4dce-a6db-2cc1626c3c62'
                            to  target ::> 'CDT_System Project'::'CDT_System'::'Operational Analysis'::'Operational Activities'::'Root Operational Activity'.'Download Data'.'52ff66f2-0ff9-4d69-9aaf-3685914a13fc' {

                                ref :>> involved = 'CDT_System Project'::'CDT_System'::'Operational Analysis'::'Operational Activities'::'Root Operational Activity'.'2602a7eb-68a7-4566-be78-8113dee1b9f4';

                            } 
                        ref action '52ff66f2-0ff9-4d69-9aaf-3685914a13fc' = 'CDT_System Project'::'CDT_System'::'Operational Analysis'::'Operational Activities'::'Root Operational Activity'.'Data is Retrieved'; 
                        connection '8188c7d7-d6f8-49ca-a18c-9d476de5faa4' : FunctionalChainInvolvementLink 
                            connect source ::> 'CDT_System Project'::'CDT_System'::'Operational Analysis'::'Operational Activities'::'Root Operational Activity'.'Download Data'.'52ff66f2-0ff9-4d69-9aaf-3685914a13fc'
                            to  target ::> 'CDT_System Project'::'CDT_System'::'Operational Analysis'::'Operational Activities'::'Root Operational Activity'.'Download Data'.'f2f58f11-f8dc-4819-8204-099fab71ac04' {

                                ref :>> involved = 'CDT_System Project'::'CDT_System'::'Operational Analysis'::'Operational Activities'::'Root Operational Activity'.'c44cfe12-e91b-4a4e-8a33-bd1d61f20822';

                            } 
                        ref action 'f2f58f11-f8dc-4819-8204-099fab71ac04' = 'CDT_System Project'::'CDT_System'::'Operational Analysis'::'Operational Activities'::'Root Operational Activity'.'Data stored'; 
                        connection '1620c072-cbf3-42ab-994f-e821b51710ed' : FunctionalChainInvolvementLink 
                            connect source ::> 'CDT_System Project'::'CDT_System'::'Operational Analysis'::'Operational Activities'::'Root Operational Activity'.'Download Data'.'f2f58f11-f8dc-4819-8204-099fab71ac04'
                            to  target ::> 'CDT_System Project'::'CDT_System'::'Operational Analysis'::'Operational Activities'::'Root Operational Activity'.'Download Data'.'cc2efe87-dbd7-45f4-a34c-6dd5ef42e3e1' {

                                ref :>> involved = 'CDT_System Project'::'CDT_System'::'Operational Analysis'::'Operational Activities'::'Root Operational Activity'.'fe72001e-f44f-402f-adea-0fe1c05c57f9';

                            } 
                        ref action 'cc2efe87-dbd7-45f4-a34c-6dd5ef42e3e1' = 'CDT_System Project'::'CDT_System'::'Operational Analysis'::'Operational Activities'::'Root Operational Activity'.'Data can be reviewed'; 
                        connection 'd1bd6090-057e-40ef-bad3-5e2eade1037e' : FunctionalChainInvolvementLink 
                            connect source ::> 'CDT_System Project'::'CDT_System'::'Operational Analysis'::'Operational Activities'::'Root Operational Activity'.'Download Data'.'cc2efe87-dbd7-45f4-a34c-6dd5ef42e3e1'
                            to  target ::> 'CDT_System Project'::'CDT_System'::'Operational Analysis'::'Operational Activities'::'Root Operational Activity'.'Download Data'.'0f78b270-bd7b-4ffb-9f70-83789bf735fb' {

                                ref :>> involved = 'CDT_System Project'::'CDT_System'::'Operational Analysis'::'Operational Activities'::'Root Operational Activity'.'dccba68c-687f-4cd3-a531-ef242d5ef3c4';

                            } 
                        ref action '0f78b270-bd7b-4ffb-9f70-83789bf735fb' = 'CDT_System Project'::'CDT_System'::'Operational Analysis'::'Operational Activities'::'Root Operational Activity'.'Executes Policies'; 
                        connection 'b432ff25-a836-4d49-9822-c5b3ccd9ac0a' : FunctionalChainInvolvementLink 
                            connect source ::> 'CDT_System Project'::'CDT_System'::'Operational Analysis'::'Operational Activities'::'Root Operational Activity'.'Download Data'.'0f78b270-bd7b-4ffb-9f70-83789bf735fb'
                            to  target ::> 'CDT_System Project'::'CDT_System'::'Operational Analysis'::'Operational Activities'::'Root Operational Activity'.'Download Data'.'6631cf89-6d79-4e67-8151-62419b4a393c' {

                                ref :>> involved = 'CDT_System Project'::'CDT_System'::'Operational Analysis'::'Operational Activities'::'Root Operational Activity'.'0e0310d4-9d6f-4cef-a541-c834c8e9b58e';

                            } 
                        ref action '6631cf89-6d79-4e67-8151-62419b4a393c' = 'CDT_System Project'::'CDT_System'::'Operational Analysis'::'Operational Activities'::'Root Operational Activity'.'Generates Reports'; 
                        connection '0514099d-8af5-4562-9460-ac2539d5eae1' : FunctionalChainInvolvementLink 
                            connect source ::> 'CDT_System Project'::'CDT_System'::'Operational Analysis'::'Operational Activities'::'Root Operational Activity'.'Download Data'.'6631cf89-6d79-4e67-8151-62419b4a393c'
                            to  target ::> 'CDT_System Project'::'CDT_System'::'Operational Analysis'::'Operational Activities'::'Root Operational Activity'.'Download Data'.'482c3a3c-024e-4d8c-bba9-896fbf28cd0e' {

                                ref :>> involved = 'CDT_System Project'::'CDT_System'::'Operational Analysis'::'Operational Activities'::'Root Operational Activity'.'a484ffff-72e5-4be8-b821-7cd0c2913aaa';

                            } 
                        ref action '482c3a3c-024e-4d8c-bba9-896fbf28cd0e' = 'CDT_System Project'::'CDT_System'::'Operational Analysis'::'Operational Activities'::'Root Operational Activity'.'Report Received'; 
                        connection '87e3286a-0da7-40aa-8132-5271251b8e64' : FunctionalChainInvolvementLink 
                            connect source ::> 'CDT_System Project'::'CDT_System'::'Operational Analysis'::'Operational Activities'::'Root Operational Activity'.'Download Data'.'6631cf89-6d79-4e67-8151-62419b4a393c'
                            to  target ::> 'CDT_System Project'::'CDT_System'::'Operational Analysis'::'Operational Activities'::'Root Operational Activity'.'Download Data'.'a1539aac-49cd-456d-a690-ad8d730bf5a6' {

                                ref :>> involved = 'CDT_System Project'::'CDT_System'::'Operational Analysis'::'Operational Activities'::'Root Operational Activity'.'2e48a379-88dc-45da-a6a5-ba3b8626b35d';

                            } 
                        ref action 'a1539aac-49cd-456d-a690-ad8d730bf5a6' = 'CDT_System Project'::'CDT_System'::'Operational Analysis'::'Operational Activities'::'Root Operational Activity'.'Report Received'; 
                        connection '3c43dc2f-42b9-4d92-91bf-0b93c19dd9a0' : FunctionalChainInvolvementLink 
                            connect source ::> 'CDT_System Project'::'CDT_System'::'Operational Analysis'::'Operational Activities'::'Root Operational Activity'.'Download Data'.'6631cf89-6d79-4e67-8151-62419b4a393c'
                            to  target ::> 'CDT_System Project'::'CDT_System'::'Operational Analysis'::'Operational Activities'::'Root Operational Activity'.'Download Data'.'96f31f2e-dfed-4cec-9ed8-e0822bb714cc' {

                                ref :>> involved = 'CDT_System Project'::'CDT_System'::'Operational Analysis'::'Operational Activities'::'Root Operational Activity'.'77316904-b9de-4066-94c9-c7826ce9a81f';

                            } 
                        ref action '96f31f2e-dfed-4cec-9ed8-e0822bb714cc' = 'CDT_System Project'::'CDT_System'::'Operational Analysis'::'Operational Activities'::'Root Operational Activity'.'Report received'; 
                    }  
                    action 'Detect Concussion' : OperationalProcess  { 
                        attribute :>> kind = FunctionalChainKind::SIMPLE; 
                        connection '3c1df7d9-cc2b-4808-8c29-34a3f1eb5354' : FunctionalChainInvolvementLink 
                            connect source ::> 'CDT_System Project'::'CDT_System'::'Operational Analysis'::'Operational Activities'::'Root Operational Activity'.'Detect Concussion'.'cd5e97c8-78f3-4777-9395-22087b63e97d'
                            to  target ::> 'CDT_System Project'::'CDT_System'::'Operational Analysis'::'Operational Activities'::'Root Operational Activity'.'Detect Concussion'.'55f4d158-2f5a-487f-8164-af53016148cc' {

                                ref :>> involved = 'CDT_System Project'::'CDT_System'::'Operational Analysis'::'Operational Activities'::'Root Operational Activity'.'ff3820bc-b497-437f-95f4-f2737ea67797';

                            } 
                        ref action '55f4d158-2f5a-487f-8164-af53016148cc' = 'CDT_System Project'::'CDT_System'::'Operational Analysis'::'Operational Activities'::'Root Operational Activity'.'Helmet Receives a Hit'; 
                        ref action 'cd5e97c8-78f3-4777-9395-22087b63e97d' = 'CDT_System Project'::'CDT_System'::'Operational Analysis'::'Operational Activities'::'Root Operational Activity'.'Athlete Particpates in Activity'; 
                        connection '3d509379-0a3f-4ea8-ba10-7fc3dd50a731' : FunctionalChainInvolvementLink 
                            connect source ::> 'CDT_System Project'::'CDT_System'::'Operational Analysis'::'Operational Activities'::'Root Operational Activity'.'Detect Concussion'.'55f4d158-2f5a-487f-8164-af53016148cc'
                            to  target ::> 'CDT_System Project'::'CDT_System'::'Operational Analysis'::'Operational Activities'::'Root Operational Activity'.'Detect Concussion'.'6f065541-3698-458d-b21f-38e4135ce5ab' {

                                ref :>> involved = 'CDT_System Project'::'CDT_System'::'Operational Analysis'::'Operational Activities'::'Root Operational Activity'.'e83dae9c-5680-42cd-9de3-1549042b2cbb';

                            } 
                        ref action '6f065541-3698-458d-b21f-38e4135ce5ab' = 'CDT_System Project'::'CDT_System'::'Operational Analysis'::'Operational Activities'::'Root Operational Activity'.'Device records Hit'; 
                        connection 'c4e27b6e-9d4e-40c6-a47f-57aed6f2ed25' : FunctionalChainInvolvementLink 
                            connect source ::> 'CDT_System Project'::'CDT_System'::'Operational Analysis'::'Operational Activities'::'Root Operational Activity'.'Detect Concussion'.'6f065541-3698-458d-b21f-38e4135ce5ab'
                            to  target ::> 'CDT_System Project'::'CDT_System'::'Operational Analysis'::'Operational Activities'::'Root Operational Activity'.'Detect Concussion'.'139d64a5-2aec-4a75-a259-f2c275da4400' {

                                ref :>> involved = 'CDT_System Project'::'CDT_System'::'Operational Analysis'::'Operational Activities'::'Root Operational Activity'.'e34f782f-a339-4564-b4b3-b0ca33af8177';

                            } 
                        ref action '139d64a5-2aec-4a75-a259-f2c275da4400' = 'CDT_System Project'::'CDT_System'::'Operational Analysis'::'Operational Activities'::'Root Operational Activity'.'Device alerts possible Concussion'; 
                        connection 'ad163dc0-0bf6-4926-add2-fb65fd63d783' : FunctionalChainInvolvementLink 
                            connect source ::> 'CDT_System Project'::'CDT_System'::'Operational Analysis'::'Operational Activities'::'Root Operational Activity'.'Detect Concussion'.'6f065541-3698-458d-b21f-38e4135ce5ab'
                            to  target ::> 'CDT_System Project'::'CDT_System'::'Operational Analysis'::'Operational Activities'::'Root Operational Activity'.'Detect Concussion'.'b302a266-f4f3-4c42-a399-8b86c14078ba' {

                                ref :>> involved = 'CDT_System Project'::'CDT_System'::'Operational Analysis'::'Operational Activities'::'Root Operational Activity'.'662fa0ed-403d-4a48-8994-cd28e044b832';

                            } 
                        ref action 'b302a266-f4f3-4c42-a399-8b86c14078ba' = 'CDT_System Project'::'CDT_System'::'Operational Analysis'::'Operational Activities'::'Root Operational Activity'.'Data is Retrieved'; 
                        connection '62d772c8-78e3-46f1-8ec9-d1e5fa388ea2' : FunctionalChainInvolvementLink 
                            connect source ::> 'CDT_System Project'::'CDT_System'::'Operational Analysis'::'Operational Activities'::'Root Operational Activity'.'Detect Concussion'.'139d64a5-2aec-4a75-a259-f2c275da4400'
                            to  target ::> 'CDT_System Project'::'CDT_System'::'Operational Analysis'::'Operational Activities'::'Root Operational Activity'.'Detect Concussion'.'3d2b0862-2860-4346-acdb-bd45908b3106' {

                                ref :>> involved = 'CDT_System Project'::'CDT_System'::'Operational Analysis'::'Operational Activities'::'Root Operational Activity'.'e71caa94-b428-41fe-93e0-c3c148b57ac5';

                            } 
                        ref action '3d2b0862-2860-4346-acdb-bd45908b3106' = 'CDT_System Project'::'CDT_System'::'Operational Analysis'::'Operational Activities'::'Root Operational Activity'.'Trainer Recieves Concussion Alert'; 
                    }  
                    action 'Aquire System' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Create profiles for Athletes' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Create Unique IDs for Athlete' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Provide Data for Profile' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Recieve ID' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Store Profile' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Create Unique IDs' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Provide ID to Athlete' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Assemble System Components' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Provide access to helmet mounting' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Provide access to sensing device mounting' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Prep the device for use' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Insert ID into Sensing Device' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Recieve ID' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Enable Secure Collection' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Place on Helmut' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Receive Athlete ' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Enable Monitoring' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Recieve Enabled Signal from Athelete Helmut' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Provide ID Information' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Athlete Particpates in Activity' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Device' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Trainer Recieves Concussion Alert' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Yield to Evaluation' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Data is Retrieved' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Data stored' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Data can be reviewed' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Report Received' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Report Received' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Report received' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Executes Policies' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Established Concussion Policy' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Generates Reports' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Helmet Receives a Hit' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Device records Hit' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    action 'Device alerts possible Concussion' : OperationalActivity  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    connection 'cc920cd2-9f5a-4453-b358-341dcd2a252b' : OAInteraction 
                        connect source ::> 'CDT_System Project'::'CDT_System'::'Operational Analysis'::'Operational Activities'::'Root Operational Activity'.'Aquire System'
                        to  target ::> 'CDT_System Project'::'CDT_System'::'Operational Analysis'::'Operational Activities'::'Root Operational Activity'.'Create profiles for Athletes' { 
                        attribute :>> isMulticast = false; 
                        attribute :>> kindOfRate = RateKind::Unspecified; 
                        attribute :>> isMultireceive = false; 
                        attribute :>> interfaceName = "System"; 
                    }  
                    connection '8aa3c385-d166-42b6-8aa7-42fb00b348dd' : OAInteraction 
                        connect source ::> 'CDT_System Project'::'CDT_System'::'Operational Analysis'::'Operational Activities'::'Root Operational Activity'.'Provide Data for Profile'
                        to  target ::> 'CDT_System Project'::'CDT_System'::'Operational Analysis'::'Operational Activities'::'Root Operational Activity'.'Create profiles for Athletes' { 
                        attribute :>> isMulticast = false; 
                        attribute :>> kindOfRate = RateKind::Unspecified; 
                        attribute :>> isMultireceive = false; 
                        attribute :>> interfaceName = "Athlete Data"; 
                    }  
                    connection '96cd2019-7155-4e26-9482-b59e3d887b05' : OAInteraction 
                        connect source ::> 'CDT_System Project'::'CDT_System'::'Operational Analysis'::'Operational Activities'::'Root Operational Activity'.'Create profiles for Athletes'
                        to  target ::> 'CDT_System Project'::'CDT_System'::'Operational Analysis'::'Operational Activities'::'Root Operational Activity'.'Create Unique IDs' { 
                        attribute :>> isMulticast = false; 
                        attribute :>> kindOfRate = RateKind::Unspecified; 
                        attribute :>> isMultireceive = false; 
                        attribute :>> interfaceName = "Profile Data"; 
                    }  
                    connection 'b4b1baea-ff21-4412-be81-677404a3aff8' : OAInteraction 
                        connect source ::> 'CDT_System Project'::'CDT_System'::'Operational Analysis'::'Operational Activities'::'Root Operational Activity'.'Create Unique IDs'
                        to  target ::> 'CDT_System Project'::'CDT_System'::'Operational Analysis'::'Operational Activities'::'Root Operational Activity'.'Create Unique IDs for Athlete' { 
                        attribute :>> isMulticast = false; 
                        attribute :>> kindOfRate = RateKind::Unspecified; 
                        attribute :>> isMultireceive = false; 
                        attribute :>> interfaceName = "ID"; 
                    }  
                    connection 'b3bed4c5-e260-48f0-bfbe-f8e400986465' : OAInteraction 
                        connect source ::> 'CDT_System Project'::'CDT_System'::'Operational Analysis'::'Operational Activities'::'Root Operational Activity'.'Create profiles for Athletes'
                        to  target ::> 'CDT_System Project'::'CDT_System'::'Operational Analysis'::'Operational Activities'::'Root Operational Activity'.'Store Profile' { 
                        attribute :>> isMulticast = false; 
                        attribute :>> kindOfRate = RateKind::Unspecified; 
                        attribute :>> isMultireceive = false; 
                        attribute :>> interfaceName = "Athlete Profile"; 
                    }  
                    connection 'f8c5c195-2105-4cfc-b95f-c2a47986f8ed' : OAInteraction 
                        connect source ::> 'CDT_System Project'::'CDT_System'::'Operational Analysis'::'Operational Activities'::'Root Operational Activity'.'Provide ID to Athlete'
                        to  target ::> 'CDT_System Project'::'CDT_System'::'Operational Analysis'::'Operational Activities'::'Root Operational Activity'.'Recieve ID' { 
                        attribute :>> isMulticast = false; 
                        attribute :>> kindOfRate = RateKind::Unspecified; 
                        attribute :>> isMultireceive = false; 
                        attribute :>> interfaceName = "ID Card"; 
                    }  
                    connection '43ebd273-9008-4d4a-bbbe-c0a6fa954cc6' : OAInteraction 
                        connect source ::> 'CDT_System Project'::'CDT_System'::'Operational Analysis'::'Operational Activities'::'Root Operational Activity'.'Create Unique IDs for Athlete'
                        to  target ::> 'CDT_System Project'::'CDT_System'::'Operational Analysis'::'Operational Activities'::'Root Operational Activity'.'Provide ID to Athlete' { 
                        attribute :>> isMulticast = false; 
                        attribute :>> kindOfRate = RateKind::Unspecified; 
                        attribute :>> isMultireceive = false; 
                        attribute :>> interfaceName = "ID Device"; 
                    }  
                    connection 'a58925f4-2c77-4d13-a5a8-ab0774fcf3e6' : OAInteraction 
                        connect source ::> 'CDT_System Project'::'CDT_System'::'Operational Analysis'::'Operational Activities'::'Root Operational Activity'.'Aquire System'
                        to  target ::> 'CDT_System Project'::'CDT_System'::'Operational Analysis'::'Operational Activities'::'Root Operational Activity'.'Assemble System Components' { 
                        attribute :>> isMulticast = false; 
                        attribute :>> kindOfRate = RateKind::Unspecified; 
                        attribute :>> isMultireceive = false; 
                        attribute :>> interfaceName = "System"; 
                    }  
                    connection 'a67bdeeb-5438-494e-b4c8-5566a801ffa9' : OAInteraction 
                        connect source ::> 'CDT_System Project'::'CDT_System'::'Operational Analysis'::'Operational Activities'::'Root Operational Activity'.'Provide access to helmet mounting'
                        to  target ::> 'CDT_System Project'::'CDT_System'::'Operational Analysis'::'Operational Activities'::'Root Operational Activity'.'Assemble System Components' { 
                        attribute :>> isMulticast = false; 
                        attribute :>> kindOfRate = RateKind::Unspecified; 
                        attribute :>> isMultireceive = false; 
                        attribute :>> interfaceName = "helmet mounting"; 
                    }  
                    connection '8536e8a8-d249-4f41-8ae0-a99b8f0f2bac' : OAInteraction 
                        connect source ::> 'CDT_System Project'::'CDT_System'::'Operational Analysis'::'Operational Activities'::'Root Operational Activity'.'Provide access to sensing device mounting'
                        to  target ::> 'CDT_System Project'::'CDT_System'::'Operational Analysis'::'Operational Activities'::'Root Operational Activity'.'Assemble System Components' { 
                        attribute :>> isMulticast = false; 
                        attribute :>> kindOfRate = RateKind::Unspecified; 
                        attribute :>> isMultireceive = false; 
                        attribute :>> interfaceName = "sensor mounting"; 
                    }  
                    connection '478e664f-6d60-4169-bda0-13ca1ce73db5' : OAInteraction 
                        connect source ::> 'CDT_System Project'::'CDT_System'::'Operational Analysis'::'Operational Activities'::'Root Operational Activity'.'Assemble System Components'
                        to  target ::> 'CDT_System Project'::'CDT_System'::'Operational Analysis'::'Operational Activities'::'Root Operational Activity'.'Prep the device for use' { 
                        attribute :>> isMulticast = false; 
                        attribute :>> kindOfRate = RateKind::Unspecified; 
                        attribute :>> isMultireceive = false; 
                        attribute :>> interfaceName = "Assembled System"; 
                    }  
                    connection '6ae929bd-82fc-49f5-a5d0-e7f201978207' : OAInteraction 
                        connect source ::> 'CDT_System Project'::'CDT_System'::'Operational Analysis'::'Operational Activities'::'Root Operational Activity'.'Recieve ID'
                        to  target ::> 'CDT_System Project'::'CDT_System'::'Operational Analysis'::'Operational Activities'::'Root Operational Activity'.'Insert ID into Sensing Device' { 
                        attribute :>> isMulticast = false; 
                        attribute :>> kindOfRate = RateKind::Unspecified; 
                        attribute :>> isMultireceive = false; 
                        attribute :>> interfaceName = "ID"; 
                    }  
                    connection '8692c5e2-7f99-4997-9988-3f6afa1e7099' : OAInteraction 
                        connect source ::> 'CDT_System Project'::'CDT_System'::'Operational Analysis'::'Operational Activities'::'Root Operational Activity'.'Insert ID into Sensing Device'
                        to  target ::> 'CDT_System Project'::'CDT_System'::'Operational Analysis'::'Operational Activities'::'Root Operational Activity'.'Recieve ID' { 
                        attribute :>> isMulticast = false; 
                        attribute :>> kindOfRate = RateKind::Unspecified; 
                        attribute :>> isMultireceive = false; 
                        attribute :>> interfaceName = "ID"; 
                    }  
                    connection '67a031db-38ff-43b0-929a-aeae5ce7c739' : OAInteraction 
                        connect source ::> 'CDT_System Project'::'CDT_System'::'Operational Analysis'::'Operational Activities'::'Root Operational Activity'.'Recieve ID'
                        to  target ::> 'CDT_System Project'::'CDT_System'::'Operational Analysis'::'Operational Activities'::'Root Operational Activity'.'Enable Secure Collection' { 
                        attribute :>> isMulticast = false; 
                        attribute :>> kindOfRate = RateKind::Unspecified; 
                        attribute :>> isMultireceive = false; 
                        attribute :>> interfaceName = "Athlete ID"; 
                    }  
                    connection '847cf44e-6cd6-43b0-8c34-e69ddcea37fb' : OAInteraction 
                        connect source ::> 'CDT_System Project'::'CDT_System'::'Operational Analysis'::'Operational Activities'::'Root Operational Activity'.'Enable Secure Collection'
                        to  target ::> 'CDT_System Project'::'CDT_System'::'Operational Analysis'::'Operational Activities'::'Root Operational Activity'.'Enable Monitoring' { 
                        attribute :>> isMulticast = false; 
                        attribute :>> kindOfRate = RateKind::Unspecified; 
                        attribute :>> isMultireceive = false; 
                        attribute :>> interfaceName = "Sensor Ready"; 
                    }  
                    connection 'dda5962e-7600-48b7-9539-8d8221660ea2' : OAInteraction 
                        connect source ::> 'CDT_System Project'::'CDT_System'::'Operational Analysis'::'Operational Activities'::'Root Operational Activity'.'Receive Athlete '
                        to  target ::> 'CDT_System Project'::'CDT_System'::'Operational Analysis'::'Operational Activities'::'Root Operational Activity'.'Enable Monitoring' { 
                        attribute :>> isMulticast = false; 
                        attribute :>> kindOfRate = RateKind::Unspecified; 
                        attribute :>> isMultireceive = false; 
                        attribute :>> interfaceName = "Helmet Motion"; 
                    }  
                    connection '8558f31b-5008-4689-b4e7-d6fe30fbcb7e' : OAInteraction 
                        connect source ::> 'CDT_System Project'::'CDT_System'::'Operational Analysis'::'Operational Activities'::'Root Operational Activity'.'Place on Helmut'
                        to  target ::> 'CDT_System Project'::'CDT_System'::'Operational Analysis'::'Operational Activities'::'Root Operational Activity'.'Receive Athlete ' { 
                        attribute :>> isMulticast = false; 
                        attribute :>> kindOfRate = RateKind::Unspecified; 
                        attribute :>> isMultireceive = false; 
                        attribute :>> interfaceName = "Head "; 
                    }  
                    connection '675e0c82-d4c3-4978-b1e5-074e665f8324' : OAInteraction 
                        connect source ::> 'CDT_System Project'::'CDT_System'::'Operational Analysis'::'Operational Activities'::'Root Operational Activity'.'Insert ID into Sensing Device'
                        to  target ::> 'CDT_System Project'::'CDT_System'::'Operational Analysis'::'Operational Activities'::'Root Operational Activity'.'Place on Helmut' { 
                        attribute :>> isMulticast = false; 
                        attribute :>> kindOfRate = RateKind::Unspecified; 
                        attribute :>> isMultireceive = false; 
                        attribute :>> interfaceName = "Ready to put on Helmut"; 
                    }  
                    connection 'ad8be7eb-6edc-42f9-adc8-8d5f8731b545' : OAInteraction 
                        connect source ::> 'CDT_System Project'::'CDT_System'::'Operational Analysis'::'Operational Activities'::'Root Operational Activity'.'Enable Monitoring'
                        to  target ::> 'CDT_System Project'::'CDT_System'::'Operational Analysis'::'Operational Activities'::'Root Operational Activity'.'Recieve Enabled Signal from Athelete Helmut' { 
                        attribute :>> isMulticast = false; 
                        attribute :>> kindOfRate = RateKind::Unspecified; 
                        attribute :>> isMultireceive = false; 
                        attribute :>> interfaceName = "Enable Signal"; 
                    }  
                    connection '66c670f2-93c8-4b31-bc85-1625e146fab8' : OAInteraction 
                        connect source ::> 'CDT_System Project'::'CDT_System'::'Operational Analysis'::'Operational Activities'::'Root Operational Activity'.'Provide ID Information'
                        to  target ::> 'CDT_System Project'::'CDT_System'::'Operational Analysis'::'Operational Activities'::'Root Operational Activity'.'Enable Secure Collection' { 
                        attribute :>> isMulticast = false; 
                        attribute :>> kindOfRate = RateKind::Unspecified; 
                        attribute :>> isMultireceive = false; 
                        attribute :>> interfaceName = "Device ID "; 
                    }  
                    connection '94b3d2fd-0513-4353-9099-489e88449ef3' : OAInteraction 
                        connect source ::> 'CDT_System Project'::'CDT_System'::'Operational Analysis'::'Operational Activities'::'Root Operational Activity'.'Aquire System'
                        to  target ::> 'CDT_System Project'::'CDT_System'::'Operational Analysis'::'Operational Activities'::'Root Operational Activity'.'Established Concussion Policy' { 
                        attribute :>> isMulticast = false; 
                        attribute :>> kindOfRate = RateKind::Unspecified; 
                        attribute :>> isMultireceive = false; 
                        attribute :>> interfaceName = "System "; 
                    }  
                    connection '1564ebdc-caf5-41b3-bfba-423d75a5b19f' : OAInteraction 
                        connect source ::> 'CDT_System Project'::'CDT_System'::'Operational Analysis'::'Operational Activities'::'Root Operational Activity'.'Established Concussion Policy'
                        to  target ::> 'CDT_System Project'::'CDT_System'::'Operational Analysis'::'Operational Activities'::'Root Operational Activity'.'Trainer Recieves Concussion Alert' { 
                        attribute :>> isMulticast = false; 
                        attribute :>> kindOfRate = RateKind::Unspecified; 
                        attribute :>> isMultireceive = false; 
                        attribute :>> interfaceName = "Concussion Policy"; 
                    }  
                    connection '0515a2c6-03ae-4443-b3da-706fd1554f0b' : OAInteraction 
                        connect source ::> 'CDT_System Project'::'CDT_System'::'Operational Analysis'::'Operational Activities'::'Root Operational Activity'.'Trainer Recieves Concussion Alert'
                        to  target ::> 'CDT_System Project'::'CDT_System'::'Operational Analysis'::'Operational Activities'::'Root Operational Activity'.'Yield to Evaluation' { 
                        attribute :>> isMulticast = false; 
                        attribute :>> kindOfRate = RateKind::Unspecified; 
                        attribute :>> isMultireceive = false; 
                        attribute :>> interfaceName = "Alert"; 
                    }  
                    connection 'c44cfe12-e91b-4a4e-8a33-bd1d61f20822' : OAInteraction 
                        connect source ::> 'CDT_System Project'::'CDT_System'::'Operational Analysis'::'Operational Activities'::'Root Operational Activity'.'Data is Retrieved'
                        to  target ::> 'CDT_System Project'::'CDT_System'::'Operational Analysis'::'Operational Activities'::'Root Operational Activity'.'Data stored' { 
                        attribute :>> isMulticast = false; 
                        attribute :>> kindOfRate = RateKind::Unspecified; 
                        attribute :>> isMultireceive = false; 
                        attribute :>> interfaceName = "Recorded Data"; 
                    }  
                    connection 'fe72001e-f44f-402f-adea-0fe1c05c57f9' : OAInteraction 
                        connect source ::> 'CDT_System Project'::'CDT_System'::'Operational Analysis'::'Operational Activities'::'Root Operational Activity'.'Data stored'
                        to  target ::> 'CDT_System Project'::'CDT_System'::'Operational Analysis'::'Operational Activities'::'Root Operational Activity'.'Data can be reviewed' { 
                        attribute :>> isMulticast = false; 
                        attribute :>> kindOfRate = RateKind::Unspecified; 
                        attribute :>> isMultireceive = false; 
                        attribute :>> interfaceName = "Stored Data "; 
                    }  
                    connection 'dccba68c-687f-4cd3-a531-ef242d5ef3c4' : OAInteraction 
                        connect source ::> 'CDT_System Project'::'CDT_System'::'Operational Analysis'::'Operational Activities'::'Root Operational Activity'.'Data can be reviewed'
                        to  target ::> 'CDT_System Project'::'CDT_System'::'Operational Analysis'::'Operational Activities'::'Root Operational Activity'.'Executes Policies' { 
                        attribute :>> isMulticast = false; 
                        attribute :>> kindOfRate = RateKind::Unspecified; 
                        attribute :>> isMultireceive = false; 
                        attribute :>> interfaceName = "Interaction 26"; 
                    }  
                    connection '0e0310d4-9d6f-4cef-a541-c834c8e9b58e' : OAInteraction 
                        connect source ::> 'CDT_System Project'::'CDT_System'::'Operational Analysis'::'Operational Activities'::'Root Operational Activity'.'Executes Policies'
                        to  target ::> 'CDT_System Project'::'CDT_System'::'Operational Analysis'::'Operational Activities'::'Root Operational Activity'.'Generates Reports' { 
                        attribute :>> isMulticast = false; 
                        attribute :>> kindOfRate = RateKind::Unspecified; 
                        attribute :>> isMultireceive = false; 
                        attribute :>> interfaceName = "Execute Policy"; 
                    }  
                    connection 'a484ffff-72e5-4be8-b821-7cd0c2913aaa' : OAInteraction 
                        connect source ::> 'CDT_System Project'::'CDT_System'::'Operational Analysis'::'Operational Activities'::'Root Operational Activity'.'Generates Reports'
                        to  target ::> 'CDT_System Project'::'CDT_System'::'Operational Analysis'::'Operational Activities'::'Root Operational Activity'.'Report Received' { 
                        attribute :>> isMulticast = false; 
                        attribute :>> kindOfRate = RateKind::Unspecified; 
                        attribute :>> isMultireceive = false; 
                        attribute :>> interfaceName = "Athlete Report"; 
                    }  
                    connection '2e48a379-88dc-45da-a6a5-ba3b8626b35d' : OAInteraction 
                        connect source ::> 'CDT_System Project'::'CDT_System'::'Operational Analysis'::'Operational Activities'::'Root Operational Activity'.'Generates Reports'
                        to  target ::> 'CDT_System Project'::'CDT_System'::'Operational Analysis'::'Operational Activities'::'Root Operational Activity'.'Report Received' { 
                        attribute :>> isMulticast = false; 
                        attribute :>> kindOfRate = RateKind::Unspecified; 
                        attribute :>> isMultireceive = false; 
                        attribute :>> interfaceName = "Instition Report"; 
                    }  
                    connection '77316904-b9de-4066-94c9-c7826ce9a81f' : OAInteraction 
                        connect source ::> 'CDT_System Project'::'CDT_System'::'Operational Analysis'::'Operational Activities'::'Root Operational Activity'.'Generates Reports'
                        to  target ::> 'CDT_System Project'::'CDT_System'::'Operational Analysis'::'Operational Activities'::'Root Operational Activity'.'Report received' { 
                        attribute :>> isMulticast = false; 
                        attribute :>> kindOfRate = RateKind::Unspecified; 
                        attribute :>> isMultireceive = false; 
                        attribute :>> interfaceName = "Paren Report"; 
                    }  
                    connection '2602a7eb-68a7-4566-be78-8113dee1b9f4' : OAInteraction 
                        connect source ::> 'CDT_System Project'::'CDT_System'::'Operational Analysis'::'Operational Activities'::'Root Operational Activity'.'Yield to Evaluation'
                        to  target ::> 'CDT_System Project'::'CDT_System'::'Operational Analysis'::'Operational Activities'::'Root Operational Activity'.'Data is Retrieved' { 
                        attribute :>> isMulticast = false; 
                        attribute :>> kindOfRate = RateKind::Unspecified; 
                        attribute :>> isMultireceive = false; 
                        attribute :>> interfaceName = "Evaluation"; 
                    }  
                    connection 'e71caa94-b428-41fe-93e0-c3c148b57ac5' : OAInteraction 
                        connect source ::> 'CDT_System Project'::'CDT_System'::'Operational Analysis'::'Operational Activities'::'Root Operational Activity'.'Device alerts possible Concussion'
                        to  target ::> 'CDT_System Project'::'CDT_System'::'Operational Analysis'::'Operational Activities'::'Root Operational Activity'.'Trainer Recieves Concussion Alert' { 
                        attribute :>> isMulticast = false; 
                        attribute :>> kindOfRate = RateKind::Unspecified; 
                        attribute :>> isMultireceive = false; 
                        attribute :>> interfaceName = "Concussion Alert to Trainer"; 
                    }  
                    connection 'ff3820bc-b497-437f-95f4-f2737ea67797' : OAInteraction 
                        connect source ::> 'CDT_System Project'::'CDT_System'::'Operational Analysis'::'Operational Activities'::'Root Operational Activity'.'Athlete Particpates in Activity'
                        to  target ::> 'CDT_System Project'::'CDT_System'::'Operational Analysis'::'Operational Activities'::'Root Operational Activity'.'Helmet Receives a Hit' { 
                        attribute :>> isMulticast = false; 
                        attribute :>> kindOfRate = RateKind::Unspecified; 
                        attribute :>> isMultireceive = false; 
                        attribute :>> interfaceName = "Activity"; 
                    }  
                    connection 'e83dae9c-5680-42cd-9de3-1549042b2cbb' : OAInteraction 
                        connect source ::> 'CDT_System Project'::'CDT_System'::'Operational Analysis'::'Operational Activities'::'Root Operational Activity'.'Helmet Receives a Hit'
                        to  target ::> 'CDT_System Project'::'CDT_System'::'Operational Analysis'::'Operational Activities'::'Root Operational Activity'.'Device records Hit' { 
                        attribute :>> isMulticast = false; 
                        attribute :>> kindOfRate = RateKind::Unspecified; 
                        attribute :>> isMultireceive = false; 
                        attribute :>> interfaceName = "Hit"; 
                    }  
                    connection 'e34f782f-a339-4564-b4b3-b0ca33af8177' : OAInteraction 
                        connect source ::> 'CDT_System Project'::'CDT_System'::'Operational Analysis'::'Operational Activities'::'Root Operational Activity'.'Device records Hit'
                        to  target ::> 'CDT_System Project'::'CDT_System'::'Operational Analysis'::'Operational Activities'::'Root Operational Activity'.'Device alerts possible Concussion' { 
                        attribute :>> isMulticast = false; 
                        attribute :>> kindOfRate = RateKind::Unspecified; 
                        attribute :>> isMultireceive = false; 
                        attribute :>> interfaceName = "Concussion"; 
                    }  
                    connection '662fa0ed-403d-4a48-8994-cd28e044b832' : OAInteraction 
                        connect source ::> 'CDT_System Project'::'CDT_System'::'Operational Analysis'::'Operational Activities'::'Root Operational Activity'.'Device records Hit'
                        to  target ::> 'CDT_System Project'::'CDT_System'::'Operational Analysis'::'Operational Activities'::'Root Operational Activity'.'Data is Retrieved' { 
                        attribute :>> isMulticast = false; 
                        attribute :>> kindOfRate = RateKind::Unspecified; 
                        attribute :>> isMultireceive = false; 
                        attribute :>> interfaceName = "Stored Data"; 
                    }  
                    ref :>> ownedFunctions =  ('CDT_System Project'::'CDT_System'::'Operational Analysis'::'Operational Activities'::'Root Operational Activity'.'Aquire System',
                    'CDT_System Project'::'CDT_System'::'Operational Analysis'::'Operational Activities'::'Root Operational Activity'.'Create profiles for Athletes',
                    'CDT_System Project'::'CDT_System'::'Operational Analysis'::'Operational Activities'::'Root Operational Activity'.'Create Unique IDs for Athlete',
                    'CDT_System Project'::'CDT_System'::'Operational Analysis'::'Operational Activities'::'Root Operational Activity'.'Provide Data for Profile',
                    'CDT_System Project'::'CDT_System'::'Operational Analysis'::'Operational Activities'::'Root Operational Activity'.'Recieve ID',
                    'CDT_System Project'::'CDT_System'::'Operational Analysis'::'Operational Activities'::'Root Operational Activity'.'Store Profile',
                    'CDT_System Project'::'CDT_System'::'Operational Analysis'::'Operational Activities'::'Root Operational Activity'.'Create Unique IDs',
                    'CDT_System Project'::'CDT_System'::'Operational Analysis'::'Operational Activities'::'Root Operational Activity'.'Provide ID to Athlete',
                    'CDT_System Project'::'CDT_System'::'Operational Analysis'::'Operational Activities'::'Root Operational Activity'.'Assemble System Components',
                    'CDT_System Project'::'CDT_System'::'Operational Analysis'::'Operational Activities'::'Root Operational Activity'.'Provide access to helmet mounting',
                    'CDT_System Project'::'CDT_System'::'Operational Analysis'::'Operational Activities'::'Root Operational Activity'.'Provide access to sensing device mounting',
                    'CDT_System Project'::'CDT_System'::'Operational Analysis'::'Operational Activities'::'Root Operational Activity'.'Prep the device for use',
                    'CDT_System Project'::'CDT_System'::'Operational Analysis'::'Operational Activities'::'Root Operational Activity'.'Insert ID into Sensing Device',
                    'CDT_System Project'::'CDT_System'::'Operational Analysis'::'Operational Activities'::'Root Operational Activity'.'Recieve ID',
                    'CDT_System Project'::'CDT_System'::'Operational Analysis'::'Operational Activities'::'Root Operational Activity'.'Enable Secure Collection',
                    'CDT_System Project'::'CDT_System'::'Operational Analysis'::'Operational Activities'::'Root Operational Activity'.'Place on Helmut',
                    'CDT_System Project'::'CDT_System'::'Operational Analysis'::'Operational Activities'::'Root Operational Activity'.'Receive Athlete ',
                    'CDT_System Project'::'CDT_System'::'Operational Analysis'::'Operational Activities'::'Root Operational Activity'.'Enable Monitoring',
                    'CDT_System Project'::'CDT_System'::'Operational Analysis'::'Operational Activities'::'Root Operational Activity'.'Recieve Enabled Signal from Athelete Helmut',
                    'CDT_System Project'::'CDT_System'::'Operational Analysis'::'Operational Activities'::'Root Operational Activity'.'Provide ID Information',
                    'CDT_System Project'::'CDT_System'::'Operational Analysis'::'Operational Activities'::'Root Operational Activity'.'Athlete Particpates in Activity',
                    'CDT_System Project'::'CDT_System'::'Operational Analysis'::'Operational Activities'::'Root Operational Activity'.'Device',
                    'CDT_System Project'::'CDT_System'::'Operational Analysis'::'Operational Activities'::'Root Operational Activity'.'Trainer Recieves Concussion Alert',
                    'CDT_System Project'::'CDT_System'::'Operational Analysis'::'Operational Activities'::'Root Operational Activity'.'Yield to Evaluation',
                    'CDT_System Project'::'CDT_System'::'Operational Analysis'::'Operational Activities'::'Root Operational Activity'.'Data is Retrieved',
                    'CDT_System Project'::'CDT_System'::'Operational Analysis'::'Operational Activities'::'Root Operational Activity'.'Data stored',
                    'CDT_System Project'::'CDT_System'::'Operational Analysis'::'Operational Activities'::'Root Operational Activity'.'Data can be reviewed',
                    'CDT_System Project'::'CDT_System'::'Operational Analysis'::'Operational Activities'::'Root Operational Activity'.'Report Received',
                    'CDT_System Project'::'CDT_System'::'Operational Analysis'::'Operational Activities'::'Root Operational Activity'.'Report Received',
                    'CDT_System Project'::'CDT_System'::'Operational Analysis'::'Operational Activities'::'Root Operational Activity'.'Report received',
                    'CDT_System Project'::'CDT_System'::'Operational Analysis'::'Operational Activities'::'Root Operational Activity'.'Executes Policies',
                    'CDT_System Project'::'CDT_System'::'Operational Analysis'::'Operational Activities'::'Root Operational Activity'.'Established Concussion Policy',
                    'CDT_System Project'::'CDT_System'::'Operational Analysis'::'Operational Activities'::'Root Operational Activity'.'Generates Reports',
                    'CDT_System Project'::'CDT_System'::'Operational Analysis'::'Operational Activities'::'Root Operational Activity'.'Helmet Receives a Hit',
                    'CDT_System Project'::'CDT_System'::'Operational Analysis'::'Operational Activities'::'Root Operational Activity'.'Device records Hit',
                    'CDT_System Project'::'CDT_System'::'Operational Analysis'::'Operational Activities'::'Root Operational Activity'.'Device alerts possible Concussion'); 
                    ref :>> ownedFunctionalExchanges =  ('CDT_System Project'::'CDT_System'::'Operational Analysis'::'Operational Activities'::'Root Operational Activity'.'cc920cd2-9f5a-4453-b358-341dcd2a252b',
                    'CDT_System Project'::'CDT_System'::'Operational Analysis'::'Operational Activities'::'Root Operational Activity'.'8aa3c385-d166-42b6-8aa7-42fb00b348dd',
                    'CDT_System Project'::'CDT_System'::'Operational Analysis'::'Operational Activities'::'Root Operational Activity'.'96cd2019-7155-4e26-9482-b59e3d887b05',
                    'CDT_System Project'::'CDT_System'::'Operational Analysis'::'Operational Activities'::'Root Operational Activity'.'b4b1baea-ff21-4412-be81-677404a3aff8',
                    'CDT_System Project'::'CDT_System'::'Operational Analysis'::'Operational Activities'::'Root Operational Activity'.'b3bed4c5-e260-48f0-bfbe-f8e400986465',
                    'CDT_System Project'::'CDT_System'::'Operational Analysis'::'Operational Activities'::'Root Operational Activity'.'f8c5c195-2105-4cfc-b95f-c2a47986f8ed',
                    'CDT_System Project'::'CDT_System'::'Operational Analysis'::'Operational Activities'::'Root Operational Activity'.'43ebd273-9008-4d4a-bbbe-c0a6fa954cc6',
                    'CDT_System Project'::'CDT_System'::'Operational Analysis'::'Operational Activities'::'Root Operational Activity'.'a58925f4-2c77-4d13-a5a8-ab0774fcf3e6',
                    'CDT_System Project'::'CDT_System'::'Operational Analysis'::'Operational Activities'::'Root Operational Activity'.'a67bdeeb-5438-494e-b4c8-5566a801ffa9',
                    'CDT_System Project'::'CDT_System'::'Operational Analysis'::'Operational Activities'::'Root Operational Activity'.'8536e8a8-d249-4f41-8ae0-a99b8f0f2bac',
                    'CDT_System Project'::'CDT_System'::'Operational Analysis'::'Operational Activities'::'Root Operational Activity'.'478e664f-6d60-4169-bda0-13ca1ce73db5',
                    'CDT_System Project'::'CDT_System'::'Operational Analysis'::'Operational Activities'::'Root Operational Activity'.'6ae929bd-82fc-49f5-a5d0-e7f201978207',
                    'CDT_System Project'::'CDT_System'::'Operational Analysis'::'Operational Activities'::'Root Operational Activity'.'8692c5e2-7f99-4997-9988-3f6afa1e7099',
                    'CDT_System Project'::'CDT_System'::'Operational Analysis'::'Operational Activities'::'Root Operational Activity'.'67a031db-38ff-43b0-929a-aeae5ce7c739',
                    'CDT_System Project'::'CDT_System'::'Operational Analysis'::'Operational Activities'::'Root Operational Activity'.'847cf44e-6cd6-43b0-8c34-e69ddcea37fb',
                    'CDT_System Project'::'CDT_System'::'Operational Analysis'::'Operational Activities'::'Root Operational Activity'.'dda5962e-7600-48b7-9539-8d8221660ea2',
                    'CDT_System Project'::'CDT_System'::'Operational Analysis'::'Operational Activities'::'Root Operational Activity'.'8558f31b-5008-4689-b4e7-d6fe30fbcb7e',
                    'CDT_System Project'::'CDT_System'::'Operational Analysis'::'Operational Activities'::'Root Operational Activity'.'675e0c82-d4c3-4978-b1e5-074e665f8324',
                    'CDT_System Project'::'CDT_System'::'Operational Analysis'::'Operational Activities'::'Root Operational Activity'.'ad8be7eb-6edc-42f9-adc8-8d5f8731b545',
                    'CDT_System Project'::'CDT_System'::'Operational Analysis'::'Operational Activities'::'Root Operational Activity'.'66c670f2-93c8-4b31-bc85-1625e146fab8',
                    'CDT_System Project'::'CDT_System'::'Operational Analysis'::'Operational Activities'::'Root Operational Activity'.'94b3d2fd-0513-4353-9099-489e88449ef3',
                    'CDT_System Project'::'CDT_System'::'Operational Analysis'::'Operational Activities'::'Root Operational Activity'.'1564ebdc-caf5-41b3-bfba-423d75a5b19f',
                    'CDT_System Project'::'CDT_System'::'Operational Analysis'::'Operational Activities'::'Root Operational Activity'.'0515a2c6-03ae-4443-b3da-706fd1554f0b',
                    'CDT_System Project'::'CDT_System'::'Operational Analysis'::'Operational Activities'::'Root Operational Activity'.'c44cfe12-e91b-4a4e-8a33-bd1d61f20822',
                    'CDT_System Project'::'CDT_System'::'Operational Analysis'::'Operational Activities'::'Root Operational Activity'.'fe72001e-f44f-402f-adea-0fe1c05c57f9',
                    'CDT_System Project'::'CDT_System'::'Operational Analysis'::'Operational Activities'::'Root Operational Activity'.'dccba68c-687f-4cd3-a531-ef242d5ef3c4',
                    'CDT_System Project'::'CDT_System'::'Operational Analysis'::'Operational Activities'::'Root Operational Activity'.'0e0310d4-9d6f-4cef-a541-c834c8e9b58e',
                    'CDT_System Project'::'CDT_System'::'Operational Analysis'::'Operational Activities'::'Root Operational Activity'.'a484ffff-72e5-4be8-b821-7cd0c2913aaa',
                    'CDT_System Project'::'CDT_System'::'Operational Analysis'::'Operational Activities'::'Root Operational Activity'.'2e48a379-88dc-45da-a6a5-ba3b8626b35d',
                    'CDT_System Project'::'CDT_System'::'Operational Analysis'::'Operational Activities'::'Root Operational Activity'.'77316904-b9de-4066-94c9-c7826ce9a81f',
                    'CDT_System Project'::'CDT_System'::'Operational Analysis'::'Operational Activities'::'Root Operational Activity'.'2602a7eb-68a7-4566-be78-8113dee1b9f4',
                    'CDT_System Project'::'CDT_System'::'Operational Analysis'::'Operational Activities'::'Root Operational Activity'.'e71caa94-b428-41fe-93e0-c3c148b57ac5',
                    'CDT_System Project'::'CDT_System'::'Operational Analysis'::'Operational Activities'::'Root Operational Activity'.'ff3820bc-b497-437f-95f4-f2737ea67797',
                    'CDT_System Project'::'CDT_System'::'Operational Analysis'::'Operational Activities'::'Root Operational Activity'.'e83dae9c-5680-42cd-9de3-1549042b2cbb',
                    'CDT_System Project'::'CDT_System'::'Operational Analysis'::'Operational Activities'::'Root Operational Activity'.'e34f782f-a339-4564-b4b3-b0ca33af8177',
                    'CDT_System Project'::'CDT_System'::'Operational Analysis'::'Operational Activities'::'Root Operational Activity'.'662fa0ed-403d-4a48-8994-cd28e044b832'); 
                }  
            } 
            package  'Interfaces' {
                @PackageMeta {
                    type = "InterfacePkg";
                } 
            } 
            package  'Operational Capabilities' {
                @PackageMeta {
                    type = "OperationalCapabilityPkg";
                } 
                use case 'Maintain Device' : OperationalCapability { 
                    actor 'Trainer' = 'CDT_System Project'::'CDT_System'::'Operational Analysis'::'Operational Entities'::'Trainer'; 
                    actor 'Sensing Device' = 'CDT_System Project'::'CDT_System'::'Operational Analysis'::'Operational Entities'::'Sensing Device'; 
                    actor 'Helmet' = 'CDT_System Project'::'CDT_System'::'Operational Analysis'::'Operational Entities'::'Helmet'; 
                    actor 'ID Device' = 'CDT_System Project'::'CDT_System'::'Operational Analysis'::'Operational Entities'::'ID Device'; 
                    actor 'Secure Cloud' = 'CDT_System Project'::'CDT_System'::'Operational Analysis'::'Operational Entities'::'Secure Cloud'; 
                    actor 'Athlete' = 'CDT_System Project'::'CDT_System'::'Operational Analysis'::'Operational Entities'::'Athlete'; 
                    ref action '93e1d0e3-cbf4-4211-ba60-61b761d7cf06' = 'CDT_System Project'::'CDT_System'::'Operational Analysis'::'Operational Activities'::'Root Operational Activity'.'Maintain'; 
                }  
                use case 'Download Data' : OperationalCapability { 
                    actor 'Trainer' = 'CDT_System Project'::'CDT_System'::'Operational Analysis'::'Operational Entities'::'Trainer'; 
                    actor 'Parent' = 'CDT_System Project'::'CDT_System'::'Operational Analysis'::'Operational Entities'::'Parent'; 
                    actor 'Athlete' = 'CDT_System Project'::'CDT_System'::'Operational Analysis'::'Operational Entities'::'Athlete'; 
                    actor 'Instituion' = 'CDT_System Project'::'CDT_System'::'Operational Analysis'::'Operational Entities'::'Instituion'; 
                    ref action 'fff873b3-4fd5-4071-833d-07f81eaaa5cd' = 'CDT_System Project'::'CDT_System'::'Operational Analysis'::'Operational Activities'::'Root Operational Activity'.'Download Data'; 
                }  
                use case 'Activate Detection' : OperationalCapability { 
                    actor 'Athlete' = 'CDT_System Project'::'CDT_System'::'Operational Analysis'::'Operational Entities'::'Athlete'; 
                    actor 'ID Device' = 'CDT_System Project'::'CDT_System'::'Operational Analysis'::'Operational Entities'::'ID Device'; 
                    actor 'Helmet' = 'CDT_System Project'::'CDT_System'::'Operational Analysis'::'Operational Entities'::'Helmet'; 
                    actor 'Sensing Device' = 'CDT_System Project'::'CDT_System'::'Operational Analysis'::'Operational Entities'::'Sensing Device'; 
                    actor 'Secure Cloud' = 'CDT_System Project'::'CDT_System'::'Operational Analysis'::'Operational Entities'::'Secure Cloud'; 
                    ref action 'f713a187-994f-4129-8c27-d3312712ca46' = 'CDT_System Project'::'CDT_System'::'Operational Analysis'::'Operational Activities'::'Root Operational Activity'.'Activate Detection Device'; 
                }  
                use case 'Aquire Device' : OperationalCapability { 
                    actor 'Instituion' = 'CDT_System Project'::'CDT_System'::'Operational Analysis'::'Operational Entities'::'Instituion'; 
                    actor 'Trainer' = 'CDT_System Project'::'CDT_System'::'Operational Analysis'::'Operational Entities'::'Trainer'; 
                    ref action '7e1077cc-72ab-4f9f-949b-fce3a46c0b66' = 'CDT_System Project'::'CDT_System'::'Operational Analysis'::'Operational Activities'::'Root Operational Activity'.'Acquire Device'; 
                }  
                use case 'Detect Concussion' : OperationalCapability { 
                    actor 'Athlete' = 'CDT_System Project'::'CDT_System'::'Operational Analysis'::'Operational Entities'::'Athlete'; 
                    actor 'Helmet' = 'CDT_System Project'::'CDT_System'::'Operational Analysis'::'Operational Entities'::'Helmet'; 
                    actor 'Sensing Device' = 'CDT_System Project'::'CDT_System'::'Operational Analysis'::'Operational Entities'::'Sensing Device'; 
                    actor 'Trainer' = 'CDT_System Project'::'CDT_System'::'Operational Analysis'::'Operational Entities'::'Trainer'; 
                    ref action '8a652579-0524-42e5-881d-fba81beda149' = 'CDT_System Project'::'CDT_System'::'Operational Analysis'::'Operational Activities'::'Root Operational Activity'.'Detect Concussion'; 
                     
                }  
            } 
            package  'Roles' {
                @PackageMeta {
                    type = "RolePkg";
                } 
            } 
        } 
        package  'System Analysis' {
            @PackageMeta {
                type = "SystemAnalysis";
            } 
            package  'Missions' {
                @PackageMeta {
                    type = "MissionPkg";
                } 
            } 
            package  'Data' {
                @PackageMeta {
                    type = "DataPkg";
                } 
                package  'Predefined Types' {
                    @PackageMeta {
                        type = "DataPkg";
                    } 
                } 
            } 
            package  'System Functions' {
                @PackageMeta {
                    type = "SystemFunctionPkg";
                } 
                action 'Root System Function' : SystemFunction  { 
                    attribute :>> isDerived = false; 
                    attribute :>> aggregationKind = AggregationKind::UNSET; 
                    attribute :>> isFinal = false; 
                    attribute :>> isPartOfKey = false; 
                    attribute :>> kind = FunctionKind::FUNCTION; 
                    attribute :>> isMaxInclusive = false; 
                    attribute :>> isUnique = false; 
                    attribute :>> isReadOnly = false; 
                    attribute :>> isMinInclusive = false; 
                    attribute :>> isStatic = false; 
                    attribute :>> isOrdered = false; 
                    attribute :>> isAbstract = false; 
                    action 'Acquire Device' : FunctionalChain  { 
                        attribute :>> kind = FunctionalChainKind::SIMPLE; 
                        connection 'dc95257f-113b-4cc1-b78d-c3ba47f34285' : FunctionalChainInvolvementLink 
                            connect source ::> 'CDT_System Project'::'CDT_System'::'System Analysis'::'System Functions'::'Root System Function'.'Acquire Device'.'57afd5db-66e6-4982-85ce-42013ccb955e'
                            to  target ::> 'CDT_System Project'::'CDT_System'::'System Analysis'::'System Functions'::'Root System Function'.'Acquire Device'.'247862d1-6916-426e-a4bb-a2ffde405b7f' {

                                ref :>> involved = 'CDT_System Project'::'CDT_System'::'System Analysis'::'System Functions'::'Root System Function'.'81872115-c1ba-45b2-b08b-7ca26e291be6';

                            } 
                        ref action '247862d1-6916-426e-a4bb-a2ffde405b7f' = 'CDT_System Project'::'CDT_System'::'System Analysis'::'System Functions'::'Root System Function'.'Create profiles for Athletes'; 
                        ref action '57afd5db-66e6-4982-85ce-42013ccb955e' = 'CDT_System Project'::'CDT_System'::'System Analysis'::'System Functions'::'Root System Function'.'Provide Data for Profile'; 
                        connection '3e7fef50-4cdc-4075-a2bd-cf144fa2dc10' : FunctionalChainInvolvementLink 
                            connect source ::> 'CDT_System Project'::'CDT_System'::'System Analysis'::'System Functions'::'Root System Function'.'Acquire Device'.'8116924e-fe81-4291-a0ff-0ffb12864c15'
                            to  target ::> 'CDT_System Project'::'CDT_System'::'System Analysis'::'System Functions'::'Root System Function'.'Acquire Device'.'247862d1-6916-426e-a4bb-a2ffde405b7f' {

                                ref :>> involved = 'CDT_System Project'::'CDT_System'::'System Analysis'::'System Functions'::'Root System Function'.'de8b39b3-0ed2-4782-9277-3264208881a2';

                            } 
                        ref action '8116924e-fe81-4291-a0ff-0ffb12864c15' = 'CDT_System Project'::'CDT_System'::'System Analysis'::'System Functions'::'Root System Function'.'Aquire System'; 
                        connection '7030f3e7-79b3-478a-a6f8-70b97a8c67be' : FunctionalChainInvolvementLink 
                            connect source ::> 'CDT_System Project'::'CDT_System'::'System Analysis'::'System Functions'::'Root System Function'.'Acquire Device'.'247862d1-6916-426e-a4bb-a2ffde405b7f'
                            to  target ::> 'CDT_System Project'::'CDT_System'::'System Analysis'::'System Functions'::'Root System Function'.'Acquire Device'.'e5a1bb29-e3a7-4520-9142-a717ca6ec5b9' {

                                ref :>> involved = 'CDT_System Project'::'CDT_System'::'System Analysis'::'System Functions'::'Root System Function'.'3f53ac60-d0be-4996-a20c-2b17947a37f5';

                            } 
                        ref action 'e5a1bb29-e3a7-4520-9142-a717ca6ec5b9' = 'CDT_System Project'::'CDT_System'::'System Analysis'::'System Functions'::'Root System Function'.'Store Profile'; 
                        ref action '4e6c3c9d-6294-4cb2-8184-65caf8c24220' = 'CDT_System Project'::'CDT_System'::'System Analysis'::'System Functions'::'Root System Function'.'Create Unique IDs'; 
                        connection '10bafd0e-a4a2-485e-ad26-1820ee38a3cd' : FunctionalChainInvolvementLink 
                            connect source ::> 'CDT_System Project'::'CDT_System'::'System Analysis'::'System Functions'::'Root System Function'.'Acquire Device'.'247862d1-6916-426e-a4bb-a2ffde405b7f'
                            to  target ::> 'CDT_System Project'::'CDT_System'::'System Analysis'::'System Functions'::'Root System Function'.'Acquire Device'.'4e6c3c9d-6294-4cb2-8184-65caf8c24220' {

                                ref :>> involved = 'CDT_System Project'::'CDT_System'::'System Analysis'::'System Functions'::'Root System Function'.'ac6779e2-d2e5-4c8f-a9f8-079d22bd999b';

                            } 
                        ref action 'a8d22e89-2b7d-428c-bb22-3ab9ca93d6f4' = 'CDT_System Project'::'CDT_System'::'System Analysis'::'System Functions'::'Root System Function'.'Create Unique IDs for Athlete'; 
                        connection 'a0717c92-cfc3-4cff-931d-726cc2174c23' : FunctionalChainInvolvementLink 
                            connect source ::> 'CDT_System Project'::'CDT_System'::'System Analysis'::'System Functions'::'Root System Function'.'Acquire Device'.'4e6c3c9d-6294-4cb2-8184-65caf8c24220'
                            to  target ::> 'CDT_System Project'::'CDT_System'::'System Analysis'::'System Functions'::'Root System Function'.'Acquire Device'.'a8d22e89-2b7d-428c-bb22-3ab9ca93d6f4' {

                                ref :>> involved = 'CDT_System Project'::'CDT_System'::'System Analysis'::'System Functions'::'Root System Function'.'9388b363-5c8b-40de-a48b-7e6d568d8924';

                            } 
                        ref action 'd4d82ba4-875d-4bf6-b090-8b8f55da5f15' = 'CDT_System Project'::'CDT_System'::'System Analysis'::'System Functions'::'Root System Function'.'Provide ID to Athlete'; 
                        connection '21a71fe8-2350-422f-ac11-1245cf1a60ff' : FunctionalChainInvolvementLink 
                            connect source ::> 'CDT_System Project'::'CDT_System'::'System Analysis'::'System Functions'::'Root System Function'.'Acquire Device'.'a8d22e89-2b7d-428c-bb22-3ab9ca93d6f4'
                            to  target ::> 'CDT_System Project'::'CDT_System'::'System Analysis'::'System Functions'::'Root System Function'.'Acquire Device'.'d4d82ba4-875d-4bf6-b090-8b8f55da5f15' {

                                ref :>> involved = 'CDT_System Project'::'CDT_System'::'System Analysis'::'System Functions'::'Root System Function'.'d8819812-ceb3-4e0f-82f3-e5ea786c3213';

                            } 
                        ref action '98230dce-ee95-48b4-b7a1-6cfb068e0a3d' = 'CDT_System Project'::'CDT_System'::'System Analysis'::'System Functions'::'Root System Function'.'Recieve ID'; 
                        connection '7428bc7a-973a-41dd-9a6c-fcbce61215f0' : FunctionalChainInvolvementLink 
                            connect source ::> 'CDT_System Project'::'CDT_System'::'System Analysis'::'System Functions'::'Root System Function'.'Acquire Device'.'d4d82ba4-875d-4bf6-b090-8b8f55da5f15'
                            to  target ::> 'CDT_System Project'::'CDT_System'::'System Analysis'::'System Functions'::'Root System Function'.'Acquire Device'.'98230dce-ee95-48b4-b7a1-6cfb068e0a3d' {

                                ref :>> involved = 'CDT_System Project'::'CDT_System'::'System Analysis'::'System Functions'::'Root System Function'.'becfa74a-3f15-42a2-8c68-e36035328abf';

                            } 
                         
                    }  
                    action 'Maintain' : FunctionalChain  { 
                        attribute :>> kind = FunctionalChainKind::SIMPLE; 
                        connection '113e73a3-bc39-4bae-9352-d792e97e312d' : FunctionalChainInvolvementLink 
                            connect source ::> 'CDT_System Project'::'CDT_System'::'System Analysis'::'System Functions'::'Root System Function'.'Maintain'.'1a29ca55-4ec5-481c-ba2e-8d28dcf11e57'
                            to  target ::> 'CDT_System Project'::'CDT_System'::'System Analysis'::'System Functions'::'Root System Function'.'Maintain'.'34d2e08e-3e1f-4f68-8419-6f35e66466bc' {

                                ref :>> involved = 'CDT_System Project'::'CDT_System'::'System Analysis'::'System Functions'::'Root System Function'.'6e077666-2c4b-4b4f-bc52-f3c820eb640d';

                            } 
                        ref action '34d2e08e-3e1f-4f68-8419-6f35e66466bc' = 'CDT_System Project'::'CDT_System'::'System Analysis'::'System Functions'::'Root System Function'.'Assemble System Components'; 
                        ref action '1a29ca55-4ec5-481c-ba2e-8d28dcf11e57' = 'CDT_System Project'::'CDT_System'::'System Analysis'::'System Functions'::'Root System Function'.'Aquire System'; 
                        connection '10ef05a9-fda1-4bbc-ba7d-07f04190f188' : FunctionalChainInvolvementLink 
                            connect source ::> 'CDT_System Project'::'CDT_System'::'System Analysis'::'System Functions'::'Root System Function'.'Maintain'.'8415929b-f437-440d-af8c-cb8f2e4431ff'
                            to  target ::> 'CDT_System Project'::'CDT_System'::'System Analysis'::'System Functions'::'Root System Function'.'Maintain'.'34d2e08e-3e1f-4f68-8419-6f35e66466bc' {

                                ref :>> involved = 'CDT_System Project'::'CDT_System'::'System Analysis'::'System Functions'::'Root System Function'.'db063bdb-25e6-4b61-8fa6-8afa652d070e';

                            } 
                        ref action '8415929b-f437-440d-af8c-cb8f2e4431ff' = 'CDT_System Project'::'CDT_System'::'System Analysis'::'System Functions'::'Root System Function'.'Provide access to helmut mounting'; 
                        connection '608b55c0-d529-4bcc-883c-b520f30b84d7' : FunctionalChainInvolvementLink 
                            connect source ::> 'CDT_System Project'::'CDT_System'::'System Analysis'::'System Functions'::'Root System Function'.'Maintain'.'1fc64298-1cf5-46d1-8faa-def121e4c684'
                            to  target ::> 'CDT_System Project'::'CDT_System'::'System Analysis'::'System Functions'::'Root System Function'.'Maintain'.'34d2e08e-3e1f-4f68-8419-6f35e66466bc' {

                                ref :>> involved = 'CDT_System Project'::'CDT_System'::'System Analysis'::'System Functions'::'Root System Function'.'45d4d189-5015-411b-8a8d-d304a60b8cc5';

                            } 
                        ref action '1fc64298-1cf5-46d1-8faa-def121e4c684' = 'CDT_System Project'::'CDT_System'::'System Analysis'::'System Functions'::'Root System Function'.'Provide access to sensing device mounting'; 
                        connection 'a507990a-54dd-4c2c-b400-af856e67c46f' : FunctionalChainInvolvementLink 
                            connect source ::> 'CDT_System Project'::'CDT_System'::'System Analysis'::'System Functions'::'Root System Function'.'Maintain'.'34d2e08e-3e1f-4f68-8419-6f35e66466bc'
                            to  target ::> 'CDT_System Project'::'CDT_System'::'System Analysis'::'System Functions'::'Root System Function'.'Maintain'.'91a9d64d-1f67-438f-aef2-6053c86c38e1' {

                                ref :>> involved = 'CDT_System Project'::'CDT_System'::'System Analysis'::'System Functions'::'Root System Function'.'4b7db120-066b-471e-a1f8-3687241321b1';

                            } 
                        ref action '91a9d64d-1f67-438f-aef2-6053c86c38e1' = 'CDT_System Project'::'CDT_System'::'System Analysis'::'System Functions'::'Root System Function'.'Prep the device for use'; 
                         
                    }  
                    action 'Activate Detection Device' : FunctionalChain  { 
                        attribute :>> kind = FunctionalChainKind::SIMPLE; 
                        connection 'f6863e9f-e0ed-40b2-9100-0a6ba99a656d' : FunctionalChainInvolvementLink 
                            connect source ::> 'CDT_System Project'::'CDT_System'::'System Analysis'::'System Functions'::'Root System Function'.'Activate Detection Device'.'f1a1ac72-a13e-4902-bf53-939d232da730'
                            to  target ::> 'CDT_System Project'::'CDT_System'::'System Analysis'::'System Functions'::'Root System Function'.'Activate Detection Device'.'0275f790-3617-427c-9167-6a58b988fed7' {

                                ref :>> involved = 'CDT_System Project'::'CDT_System'::'System Analysis'::'System Functions'::'Root System Function'.'96aa037f-ec86-482c-abbc-444ca7fef501';

                            } 
                        ref action '0275f790-3617-427c-9167-6a58b988fed7' = 'CDT_System Project'::'CDT_System'::'System Analysis'::'System Functions'::'Root System Function'.'Insert ID into Sensing Device'; 
                        ref action 'f1a1ac72-a13e-4902-bf53-939d232da730' = 'CDT_System Project'::'CDT_System'::'System Analysis'::'System Functions'::'Root System Function'.'Recieve ID'; 
                        connection 'a8c36962-371b-4efd-8312-c589d2869184' : FunctionalChainInvolvementLink 
                            connect source ::> 'CDT_System Project'::'CDT_System'::'System Analysis'::'System Functions'::'Root System Function'.'Activate Detection Device'.'0275f790-3617-427c-9167-6a58b988fed7'
                            to  target ::> 'CDT_System Project'::'CDT_System'::'System Analysis'::'System Functions'::'Root System Function'.'Activate Detection Device'.'573a2301-c360-4cc0-a6f0-1e69610a416e' {

                                ref :>> involved = 'CDT_System Project'::'CDT_System'::'System Analysis'::'System Functions'::'Root System Function'.'6aaff874-bc5c-4b3a-8750-2b5cb9ffa876';

                            } 
                        ref action '573a2301-c360-4cc0-a6f0-1e69610a416e' = 'CDT_System Project'::'CDT_System'::'System Analysis'::'System Functions'::'Root System Function'.'Recieve ID'; 
                        connection '5d24251c-b6c9-40d8-a56c-6d62fd476cb3' : FunctionalChainInvolvementLink 
                            connect source ::> 'CDT_System Project'::'CDT_System'::'System Analysis'::'System Functions'::'Root System Function'.'Activate Detection Device'.'0275f790-3617-427c-9167-6a58b988fed7'
                            to  target ::> 'CDT_System Project'::'CDT_System'::'System Analysis'::'System Functions'::'Root System Function'.'Activate Detection Device'.'87d6a44b-4482-4556-9d7e-f64df4bcd796' {

                                ref :>> involved = 'CDT_System Project'::'CDT_System'::'System Analysis'::'System Functions'::'Root System Function'.'64ccd66f-c036-4a8e-89f0-88294cf921ff';

                            } 
                        ref action '87d6a44b-4482-4556-9d7e-f64df4bcd796' = 'CDT_System Project'::'CDT_System'::'System Analysis'::'System Functions'::'Root System Function'.'Place on Helmet'; 
                        connection '221ec37e-686b-4cb0-8310-7d622e71ffe6' : FunctionalChainInvolvementLink 
                            connect source ::> 'CDT_System Project'::'CDT_System'::'System Analysis'::'System Functions'::'Root System Function'.'Activate Detection Device'.'573a2301-c360-4cc0-a6f0-1e69610a416e'
                            to  target ::> 'CDT_System Project'::'CDT_System'::'System Analysis'::'System Functions'::'Root System Function'.'Activate Detection Device'.'c62ef722-d7c3-4e46-8a45-8d83974130d0' {

                                ref :>> involved = 'CDT_System Project'::'CDT_System'::'System Analysis'::'System Functions'::'Root System Function'.'54af6de5-a1e2-4873-9717-47cae6371e49';

                            } 
                        ref action 'c62ef722-d7c3-4e46-8a45-8d83974130d0' = 'CDT_System Project'::'CDT_System'::'System Analysis'::'System Functions'::'Root System Function'.'Enable Secure Collection'; 
                        connection '2c0a22cb-23d2-4525-bdc9-281cd3645888' : FunctionalChainInvolvementLink 
                            connect source ::> 'CDT_System Project'::'CDT_System'::'System Analysis'::'System Functions'::'Root System Function'.'Activate Detection Device'.'c62ef722-d7c3-4e46-8a45-8d83974130d0'
                            to  target ::> 'CDT_System Project'::'CDT_System'::'System Analysis'::'System Functions'::'Root System Function'.'Activate Detection Device'.'cd740eac-6115-42ed-a81b-2f271e43d4ac' {

                                ref :>> involved = 'CDT_System Project'::'CDT_System'::'System Analysis'::'System Functions'::'Root System Function'.'63588dfa-f2f9-4eb4-93de-72bac38f5fc2';

                            } 
                        ref action 'cd740eac-6115-42ed-a81b-2f271e43d4ac' = 'CDT_System Project'::'CDT_System'::'System Analysis'::'System Functions'::'Root System Function'.'Enable Monitoring'; 
                        connection 'cae08a12-8f18-4bd1-b7b3-73f2ffcaf5bc' : FunctionalChainInvolvementLink 
                            connect source ::> 'CDT_System Project'::'CDT_System'::'System Analysis'::'System Functions'::'Root System Function'.'Activate Detection Device'.'87d6a44b-4482-4556-9d7e-f64df4bcd796'
                            to  target ::> 'CDT_System Project'::'CDT_System'::'System Analysis'::'System Functions'::'Root System Function'.'Activate Detection Device'.'04869511-2c91-431d-99a8-c8901ed1ea0a' {

                                ref :>> involved = 'CDT_System Project'::'CDT_System'::'System Analysis'::'System Functions'::'Root System Function'.'7e3bc9a2-7ee0-4b84-b6a5-cb7b56fd966f';

                            } 
                        ref action '04869511-2c91-431d-99a8-c8901ed1ea0a' = 'CDT_System Project'::'CDT_System'::'System Analysis'::'System Functions'::'Root System Function'.'Receive Athlete '; 
                        connection '5c720816-e24a-4c2f-9164-7401be637c62' : FunctionalChainInvolvementLink 
                            connect source ::> 'CDT_System Project'::'CDT_System'::'System Analysis'::'System Functions'::'Root System Function'.'Activate Detection Device'.'04869511-2c91-431d-99a8-c8901ed1ea0a'
                            to  target ::> 'CDT_System Project'::'CDT_System'::'System Analysis'::'System Functions'::'Root System Function'.'Activate Detection Device'.'cd740eac-6115-42ed-a81b-2f271e43d4ac' {

                                ref :>> involved = 'CDT_System Project'::'CDT_System'::'System Analysis'::'System Functions'::'Root System Function'.'d2aa068f-0d8a-43cf-95af-f9db099ebadf';

                            } 
                        ref action '61c81411-e359-4a7e-918d-5a211576f40d' = 'CDT_System Project'::'CDT_System'::'System Analysis'::'System Functions'::'Root System Function'.'Provide ID Information'; 
                        connection 'e9a22968-a66c-4258-95ac-ad2203ebfd83' : FunctionalChainInvolvementLink 
                            connect source ::> 'CDT_System Project'::'CDT_System'::'System Analysis'::'System Functions'::'Root System Function'.'Activate Detection Device'.'61c81411-e359-4a7e-918d-5a211576f40d'
                            to  target ::> 'CDT_System Project'::'CDT_System'::'System Analysis'::'System Functions'::'Root System Function'.'Activate Detection Device'.'c62ef722-d7c3-4e46-8a45-8d83974130d0' {

                                ref :>> involved = 'CDT_System Project'::'CDT_System'::'System Analysis'::'System Functions'::'Root System Function'.'65231319-835b-4eac-8173-8c7bd196f040';

                            } 
                        ref action '3752d5c2-8f7e-4279-9e87-2bb93d4e3daf' = 'CDT_System Project'::'CDT_System'::'System Analysis'::'System Functions'::'Root System Function'.'Recieve Enabled Signal from Athelete Helmet'; 
                        connection '31fe5698-701f-4450-80f8-0785d938e59a' : FunctionalChainInvolvementLink 
                            connect source ::> 'CDT_System Project'::'CDT_System'::'System Analysis'::'System Functions'::'Root System Function'.'Activate Detection Device'.'cd740eac-6115-42ed-a81b-2f271e43d4ac'
                            to  target ::> 'CDT_System Project'::'CDT_System'::'System Analysis'::'System Functions'::'Root System Function'.'Activate Detection Device'.'3752d5c2-8f7e-4279-9e87-2bb93d4e3daf' {

                                ref :>> involved = 'CDT_System Project'::'CDT_System'::'System Analysis'::'System Functions'::'Root System Function'.'0a7f17b0-3306-4d7a-8196-b6a4818100ac';

                            } 
                         
                    }  
                    action 'Download Data' : FunctionalChain  { 
                        attribute :>> kind = FunctionalChainKind::SIMPLE; 
                        connection '152a4efa-5b1f-4df6-a991-b1fc64fc9c3f' : FunctionalChainInvolvementLink 
                            connect source ::> 'CDT_System Project'::'CDT_System'::'System Analysis'::'System Functions'::'Root System Function'.'Download Data'.'d1d245df-1a88-4c69-ad6a-ca7cd3815256'
                            to  target ::> 'CDT_System Project'::'CDT_System'::'System Analysis'::'System Functions'::'Root System Function'.'Download Data'.'46907e68-8640-4ce8-b173-95cdbca4d54e' {

                                ref :>> involved = 'CDT_System Project'::'CDT_System'::'System Analysis'::'System Functions'::'Root System Function'.'ccadc84d-edde-4250-9bde-a78ae466fbad';

                            } 
                        ref action '46907e68-8640-4ce8-b173-95cdbca4d54e' = 'CDT_System Project'::'CDT_System'::'System Analysis'::'System Functions'::'Root System Function'.'Yield to Evaluation'; 
                        ref action 'd1d245df-1a88-4c69-ad6a-ca7cd3815256' = 'CDT_System Project'::'CDT_System'::'System Analysis'::'System Functions'::'Root System Function'.'Trainer Recieves Concussion Alert'; 
                        connection 'c48b3f1f-6100-4057-9cc3-4fd75392aae7' : FunctionalChainInvolvementLink 
                            connect source ::> 'CDT_System Project'::'CDT_System'::'System Analysis'::'System Functions'::'Root System Function'.'Download Data'.'46907e68-8640-4ce8-b173-95cdbca4d54e'
                            to  target ::> 'CDT_System Project'::'CDT_System'::'System Analysis'::'System Functions'::'Root System Function'.'Download Data'.'f748fe1f-c7d1-44b4-927b-c03dfa7bed1a' {

                                ref :>> involved = 'CDT_System Project'::'CDT_System'::'System Analysis'::'System Functions'::'Root System Function'.'fcbc8312-6fba-41cd-b0ff-caf04d9dced8';

                            } 
                        ref action 'f748fe1f-c7d1-44b4-927b-c03dfa7bed1a' = 'CDT_System Project'::'CDT_System'::'System Analysis'::'System Functions'::'Root System Function'.'Data is Retrieved'; 
                        connection 'cfef3396-d75b-470e-82db-c02298d786ae' : FunctionalChainInvolvementLink 
                            connect source ::> 'CDT_System Project'::'CDT_System'::'System Analysis'::'System Functions'::'Root System Function'.'Download Data'.'f748fe1f-c7d1-44b4-927b-c03dfa7bed1a'
                            to  target ::> 'CDT_System Project'::'CDT_System'::'System Analysis'::'System Functions'::'Root System Function'.'Download Data'.'726956db-ce2f-4696-94fa-91f4813599a4' {

                                ref :>> involved = 'CDT_System Project'::'CDT_System'::'System Analysis'::'System Functions'::'Root System Function'.'db4f5ed3-3d7e-487a-b098-8da26c258ffa';

                            } 
                        ref action '726956db-ce2f-4696-94fa-91f4813599a4' = 'CDT_System Project'::'CDT_System'::'System Analysis'::'System Functions'::'Root System Function'.'Data stored'; 
                        connection 'c084f59d-1df4-430f-b320-77a8cd564db9' : FunctionalChainInvolvementLink 
                            connect source ::> 'CDT_System Project'::'CDT_System'::'System Analysis'::'System Functions'::'Root System Function'.'Download Data'.'726956db-ce2f-4696-94fa-91f4813599a4'
                            to  target ::> 'CDT_System Project'::'CDT_System'::'System Analysis'::'System Functions'::'Root System Function'.'Download Data'.'260280d3-7052-4aed-922b-f206202e894d' {

                                ref :>> involved = 'CDT_System Project'::'CDT_System'::'System Analysis'::'System Functions'::'Root System Function'.'317c24bc-f488-4511-8223-4876ad934caf';

                            } 
                        ref action '260280d3-7052-4aed-922b-f206202e894d' = 'CDT_System Project'::'CDT_System'::'System Analysis'::'System Functions'::'Root System Function'.'Data can be reviewed'; 
                        connection '3fc5bea5-5205-429a-a453-a3bc23a6b844' : FunctionalChainInvolvementLink 
                            connect source ::> 'CDT_System Project'::'CDT_System'::'System Analysis'::'System Functions'::'Root System Function'.'Download Data'.'260280d3-7052-4aed-922b-f206202e894d'
                            to  target ::> 'CDT_System Project'::'CDT_System'::'System Analysis'::'System Functions'::'Root System Function'.'Download Data'.'e839ab67-e826-40c4-9816-7583af6f43b5' {

                                ref :>> involved = 'CDT_System Project'::'CDT_System'::'System Analysis'::'System Functions'::'Root System Function'.'1e684e43-60e9-4843-a5b4-53e1b3956172';

                            } 
                        ref action 'e839ab67-e826-40c4-9816-7583af6f43b5' = 'CDT_System Project'::'CDT_System'::'System Analysis'::'System Functions'::'Root System Function'.'Executes Policies'; 
                        connection 'c5d0aa33-e0f4-47f0-bce2-81d730fa5b30' : FunctionalChainInvolvementLink 
                            connect source ::> 'CDT_System Project'::'CDT_System'::'System Analysis'::'System Functions'::'Root System Function'.'Download Data'.'e839ab67-e826-40c4-9816-7583af6f43b5'
                            to  target ::> 'CDT_System Project'::'CDT_System'::'System Analysis'::'System Functions'::'Root System Function'.'Download Data'.'bd2fabe4-73a6-4896-a892-b70a584cbad6' {

                                ref :>> involved = 'CDT_System Project'::'CDT_System'::'System Analysis'::'System Functions'::'Root System Function'.'68cb347a-561b-4144-a0e2-4e88d7e29875';

                            } 
                        ref action 'bd2fabe4-73a6-4896-a892-b70a584cbad6' = 'CDT_System Project'::'CDT_System'::'System Analysis'::'System Functions'::'Root System Function'.'Generates Reports'; 
                        connection '2085cedb-184d-4acc-b8a9-c7cf992532e3' : FunctionalChainInvolvementLink 
                            connect source ::> 'CDT_System Project'::'CDT_System'::'System Analysis'::'System Functions'::'Root System Function'.'Download Data'.'bd2fabe4-73a6-4896-a892-b70a584cbad6'
                            to  target ::> 'CDT_System Project'::'CDT_System'::'System Analysis'::'System Functions'::'Root System Function'.'Download Data'.'051e9989-3aa0-44e9-95b2-64982b542c0f' {

                                ref :>> involved = 'CDT_System Project'::'CDT_System'::'System Analysis'::'System Functions'::'Root System Function'.'7f0a842b-0f47-4a50-98b8-4116a4ed43c8';

                            } 
                        ref action '051e9989-3aa0-44e9-95b2-64982b542c0f' = 'CDT_System Project'::'CDT_System'::'System Analysis'::'System Functions'::'Root System Function'.'Report Received'; 
                        connection '50f1d6c7-01cd-471f-9681-5f4f87e6cf2e' : FunctionalChainInvolvementLink 
                            connect source ::> 'CDT_System Project'::'CDT_System'::'System Analysis'::'System Functions'::'Root System Function'.'Download Data'.'bd2fabe4-73a6-4896-a892-b70a584cbad6'
                            to  target ::> 'CDT_System Project'::'CDT_System'::'System Analysis'::'System Functions'::'Root System Function'.'Download Data'.'4a79d0fc-9158-4c3d-be7c-8ec0c2bb7fc0' {

                                ref :>> involved = 'CDT_System Project'::'CDT_System'::'System Analysis'::'System Functions'::'Root System Function'.'6067b5d5-fbf6-466c-ab48-87c045004339';

                            } 
                        ref action '4a79d0fc-9158-4c3d-be7c-8ec0c2bb7fc0' = 'CDT_System Project'::'CDT_System'::'System Analysis'::'System Functions'::'Root System Function'.'Report Received'; 
                        connection '2e04ea06-a707-4b3a-9ee3-8dfd064963d1' : FunctionalChainInvolvementLink 
                            connect source ::> 'CDT_System Project'::'CDT_System'::'System Analysis'::'System Functions'::'Root System Function'.'Download Data'.'bd2fabe4-73a6-4896-a892-b70a584cbad6'
                            to  target ::> 'CDT_System Project'::'CDT_System'::'System Analysis'::'System Functions'::'Root System Function'.'Download Data'.'4adaeda8-4481-4b64-b9db-62d7fab3db0c' {

                                ref :>> involved = 'CDT_System Project'::'CDT_System'::'System Analysis'::'System Functions'::'Root System Function'.'807a6b94-cf3b-47d4-b41c-036867b29a84';

                            } 
                        ref action '4adaeda8-4481-4b64-b9db-62d7fab3db0c' = 'CDT_System Project'::'CDT_System'::'System Analysis'::'System Functions'::'Root System Function'.'Report received'; 
                         
                    }  
                    action 'Detect Concussion' : FunctionalChain  { 
                        attribute :>> kind = FunctionalChainKind::SIMPLE; 
                        connection 'e509bd80-5c30-4fdc-81d6-9439a05e6030' : FunctionalChainInvolvementLink 
                            connect source ::> 'CDT_System Project'::'CDT_System'::'System Analysis'::'System Functions'::'Root System Function'.'Detect Concussion'.'dbb3d90d-8b1b-4677-a923-5539637e1071'
                            to  target ::> 'CDT_System Project'::'CDT_System'::'System Analysis'::'System Functions'::'Root System Function'.'Detect Concussion'.'fe16cb30-2c9b-4b6e-ba08-34b541d91c1a' {

                                ref :>> involved = 'CDT_System Project'::'CDT_System'::'System Analysis'::'System Functions'::'Root System Function'.'97a72935-6d79-46ff-b4b7-1d130ca15b47';

                            } 
                        ref action 'fe16cb30-2c9b-4b6e-ba08-34b541d91c1a' = 'CDT_System Project'::'CDT_System'::'System Analysis'::'System Functions'::'Root System Function'.'Helmet Receives a Hit'; 
                        ref action 'dbb3d90d-8b1b-4677-a923-5539637e1071' = 'CDT_System Project'::'CDT_System'::'System Analysis'::'System Functions'::'Root System Function'.'Athlete Particpates in Activity'; 
                        connection '4ebcb25a-1b3f-4822-ad0a-a349388877f2' : FunctionalChainInvolvementLink 
                            connect source ::> 'CDT_System Project'::'CDT_System'::'System Analysis'::'System Functions'::'Root System Function'.'Detect Concussion'.'fe16cb30-2c9b-4b6e-ba08-34b541d91c1a'
                            to  target ::> 'CDT_System Project'::'CDT_System'::'System Analysis'::'System Functions'::'Root System Function'.'Detect Concussion'.'c2bd4fb7-30f9-470c-b351-5cf24826f56a' {

                                ref :>> involved = 'CDT_System Project'::'CDT_System'::'System Analysis'::'System Functions'::'Root System Function'.'12f0e27a-cfda-4d15-acc7-c343637f5dee';

                            } 
                        ref action 'c2bd4fb7-30f9-470c-b351-5cf24826f56a' = 'CDT_System Project'::'CDT_System'::'System Analysis'::'System Functions'::'Root System Function'.'Device records Hit'; 
                        connection '690d758f-cb06-4c93-a481-b3fa3b2645f9' : FunctionalChainInvolvementLink 
                            connect source ::> 'CDT_System Project'::'CDT_System'::'System Analysis'::'System Functions'::'Root System Function'.'Detect Concussion'.'c2bd4fb7-30f9-470c-b351-5cf24826f56a'
                            to  target ::> 'CDT_System Project'::'CDT_System'::'System Analysis'::'System Functions'::'Root System Function'.'Detect Concussion'.'31a1d18a-4208-45f7-917c-9658c9dcf3d7' {

                                ref :>> involved = 'CDT_System Project'::'CDT_System'::'System Analysis'::'System Functions'::'Root System Function'.'4b9c774c-e9a5-431a-ad18-2f8690985890';

                            } 
                        ref action '31a1d18a-4208-45f7-917c-9658c9dcf3d7' = 'CDT_System Project'::'CDT_System'::'System Analysis'::'System Functions'::'Root System Function'.'Device alerts possible Concussion'; 
                        connection '3a4f6f96-8bcf-4708-b685-8c3efba8318f' : FunctionalChainInvolvementLink 
                            connect source ::> 'CDT_System Project'::'CDT_System'::'System Analysis'::'System Functions'::'Root System Function'.'Detect Concussion'.'c2bd4fb7-30f9-470c-b351-5cf24826f56a'
                            to  target ::> 'CDT_System Project'::'CDT_System'::'System Analysis'::'System Functions'::'Root System Function'.'Detect Concussion'.'e55f4135-dd4a-4aad-9da5-d4d88861e625' {

                                ref :>> involved = 'CDT_System Project'::'CDT_System'::'System Analysis'::'System Functions'::'Root System Function'.'f3c6d7e4-fef4-45a0-ac16-8f3392ce7aed';

                            } 
                        ref action 'e55f4135-dd4a-4aad-9da5-d4d88861e625' = 'CDT_System Project'::'CDT_System'::'System Analysis'::'System Functions'::'Root System Function'.'Data is Retrieved'; 
                        connection '70169712-8c47-4de9-ad2a-9d0601605e29' : FunctionalChainInvolvementLink 
                            connect source ::> 'CDT_System Project'::'CDT_System'::'System Analysis'::'System Functions'::'Root System Function'.'Detect Concussion'.'31a1d18a-4208-45f7-917c-9658c9dcf3d7'
                            to  target ::> 'CDT_System Project'::'CDT_System'::'System Analysis'::'System Functions'::'Root System Function'.'Detect Concussion'.'b314f636-835c-4ef1-a20a-4d2d9e5e3709' {

                                ref :>> involved = 'CDT_System Project'::'CDT_System'::'System Analysis'::'System Functions'::'Root System Function'.'8520e06a-fe44-4659-8276-5a2d135f9211';

                            } 
                        ref action 'b314f636-835c-4ef1-a20a-4d2d9e5e3709' = 'CDT_System Project'::'CDT_System'::'System Analysis'::'System Functions'::'Root System Function'.'Trainer Recieves Concussion Alert'; 
                         
                    }  
                    action 'Aquire System' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outSystem' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outSystem ' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outSystem' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'System Analysis'::'System Functions'::'Root System Function'.'Aquire System'.'outSystem',
                        'CDT_System Project'::'CDT_System'::'System Analysis'::'System Functions'::'Root System Function'.'Aquire System'.'outSystem ',
                        'CDT_System Project'::'CDT_System'::'System Analysis'::'System Functions'::'Root System Function'.'Aquire System'.'outSystem'); 
                         
                    }  
                    action 'Create profiles for Athletes' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem' : FunctionInputPort  { 
                            attribute :>> isControlType = false; 
                            attribute :>> ordering = ObjectNodeOrderingKind::FIFO; 
                            attribute :>> isControl = false; 
                            attribute :>> kindOfNode = ObjectNodeKind::Unspecified; 
                        }  
                        in port 'inAthlete Data' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outProfile Data' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outAthlete Profile' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Create profiles for Athletes'.'inSystem',
                        'CDT_System Project'::'CDT_System'::'System Analysis'::'System Functions'::'Root System Function'.'Create profiles for Athletes'.'inAthlete Data'); 
                        ref :>> outputs =  ('CDT_System Project'::'CDT_System'::'System Analysis'::'System Functions'::'Root System Function'.'Create profiles for Athletes'.'outProfile Data',
                        'CDT_System Project'::'CDT_System'::'System Analysis'::'System Functions'::'Root System Function'.'Create profiles for Athletes'.'outAthlete Profile'); 
                         
                    }  
                    action 'Create Unique IDs for Athlete' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outID Device' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Create Unique IDs for Athlete'.'inID'); 
                        ref :>> outputs =  ('CDT_System Project'::'CDT_System'::'System Analysis'::'System Functions'::'Root System Function'.'Create Unique IDs for Athlete'.'outID Device'); 
                         
                    }  
                    action 'Provide Data for Profile' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outAthlete Data' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'System Analysis'::'System Functions'::'Root System Function'.'Provide Data for Profile'.'outAthlete Data'); 
                         
                    }  
                    action 'Recieve ID' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID Card' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Recieve ID'.'inID Card'); 
                        ref :>> outputs =  ('CDT_System Project'::'CDT_System'::'System Analysis'::'System Functions'::'Root System Function'.'Recieve ID'.'outID'); 
                         
                    }  
                    action 'Store Profile' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete Profile' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Store Profile'.'inAthlete Profile'); 
                         
                    }  
                    action 'Create Unique IDs' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inProfile Data' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Create Unique IDs'.'inProfile Data'); 
                        ref :>> outputs =  ('CDT_System Project'::'CDT_System'::'System Analysis'::'System Functions'::'Root System Function'.'Create Unique IDs'.'outID'); 
                         
                    }  
                    action 'Provide ID to Athlete' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID Device' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outID Card' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Provide ID to Athlete'.'inID Device'); 
                        ref :>> outputs =  ('CDT_System Project'::'CDT_System'::'System Analysis'::'System Functions'::'Root System Function'.'Provide ID to Athlete'.'outID Card'); 
                         
                    }  
                    action 'Assemble System Components' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem' : FunctionInputPort  { 
                            attribute :>> isControlType = false; 
                            attribute :>> ordering = ObjectNodeOrderingKind::FIFO; 
                            attribute :>> isControl = false; 
                            attribute :>> kindOfNode = ObjectNodeKind::Unspecified; 
                        }  
                        in port 'inhelmut mounting' : FunctionInputPort  { 
                            attribute :>> isControlType = false; 
                            attribute :>> ordering = ObjectNodeOrderingKind::FIFO; 
                            attribute :>> isControl = false; 
                            attribute :>> kindOfNode = ObjectNodeKind::Unspecified; 
                        }  
                        in port 'insensor mounting' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outAssembled System' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Assemble System Components'.'inSystem',
                        'CDT_System Project'::'CDT_System'::'System Analysis'::'System Functions'::'Root System Function'.'Assemble System Components'.'inhelmut mounting',
                        'CDT_System Project'::'CDT_System'::'System Analysis'::'System Functions'::'Root System Function'.'Assemble System Components'.'insensor mounting'); 
                        ref :>> outputs =  ('CDT_System Project'::'CDT_System'::'System Analysis'::'System Functions'::'Root System Function'.'Assemble System Components'.'outAssembled System'); 
                         
                    }  
                    action 'Provide access to helmut mounting' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outhelmut mounting' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'System Analysis'::'System Functions'::'Root System Function'.'Provide access to helmut mounting'.'outhelmut mounting'); 
                         
                    }  
                    action 'Provide access to sensing device mounting' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outsensor mounting' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'System Analysis'::'System Functions'::'Root System Function'.'Provide access to sensing device mounting'.'outsensor mounting'); 
                         
                    }  
                    action 'Prep the device for use' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAssembled System' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Prep the device for use'.'inAssembled System'); 
                         
                    }  
                    action 'Insert ID into Sensing Device' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outReady to put on Helmut' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Insert ID into Sensing Device'.'inID'); 
                        ref :>> outputs =  ('CDT_System Project'::'CDT_System'::'System Analysis'::'System Functions'::'Root System Function'.'Insert ID into Sensing Device'.'outReady to put on Helmut',
                        'CDT_System Project'::'CDT_System'::'System Analysis'::'System Functions'::'Root System Function'.'Insert ID into Sensing Device'.'outID'); 
                         
                    }  
                    action 'Recieve ID' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outAthlete ID' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Recieve ID'.'inID'); 
                        ref :>> outputs =  ('CDT_System Project'::'CDT_System'::'System Analysis'::'System Functions'::'Root System Function'.'Recieve ID'.'outAthlete ID'); 
                         
                    }  
                    action 'Device alerts possible Concussion' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inConcussion' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outConcussion Alert to Trainer' : FunctionOutputPort  { 
                            attribute :>> isControlType = false; 
                            attribute :>> ordering = ObjectNodeOrderingKind::FIFO; 
                            attribute :>> isControl = false; 
                            attribute :>> kindOfNode = ObjectNodeKind::Unspecified; 
                            ref :>> outgoingExchangeItems =  ('CDT_System Project'::'CDT_System'::'Operational Analysis'::'Data'::'Alert'); 
                        }  
                        ref :>> inputs =  ('CDT_System Project'::'CDT_System'::'System Analysis'::'System Functions'::'Root System Function'.'Device alerts possible Concussion'.'inConcussion'); 
                        ref :>> outputs =  ('CDT_System Project'::'CDT_System'::'System Analysis'::'System Functions'::'Root System Function'.'Device alerts possible Concussion'.'outConcussion Alert to Trainer'); 
                         
                    }  
                    action 'Trainer Recieves Concussion Alert' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inConcussion Policy' : FunctionInputPort  { 
                            attribute :>> isControlType = false; 
                            attribute :>> ordering = ObjectNodeOrderingKind::FIFO; 
                            attribute :>> isControl = false; 
                            attribute :>> kindOfNode = ObjectNodeKind::Unspecified; 
                        }  
                        in port 'inConcussion Alert to Trainer' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Alert'); 
                        }  
                        out port 'outAlert' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Trainer Recieves Concussion Alert'.'inConcussion Policy',
                        'CDT_System Project'::'CDT_System'::'System Analysis'::'System Functions'::'Root System Function'.'Trainer Recieves Concussion Alert'.'inConcussion Alert to Trainer'); 
                        ref :>> outputs =  ('CDT_System Project'::'CDT_System'::'System Analysis'::'System Functions'::'Root System Function'.'Trainer Recieves Concussion Alert'.'outAlert'); 
                         
                    }  
                    action 'Device records Hit' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inHit' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outConcussion' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outStored Data' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Device records Hit'.'inHit'); 
                        ref :>> outputs =  ('CDT_System Project'::'CDT_System'::'System Analysis'::'System Functions'::'Root System Function'.'Device records Hit'.'outConcussion',
                        'CDT_System Project'::'CDT_System'::'System Analysis'::'System Functions'::'Root System Function'.'Device records Hit'.'outStored Data'); 
                         
                    }  
                    action 'Enable Secure Collection' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete ID' : FunctionInputPort  { 
                            attribute :>> isControlType = false; 
                            attribute :>> ordering = ObjectNodeOrderingKind::FIFO; 
                            attribute :>> isControl = false; 
                            attribute :>> kindOfNode = ObjectNodeKind::Unspecified; 
                        }  
                        in port 'inDevice ID ' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outSensor Ready' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Enable Secure Collection'.'inAthlete ID',
                        'CDT_System Project'::'CDT_System'::'System Analysis'::'System Functions'::'Root System Function'.'Enable Secure Collection'.'inDevice ID '); 
                        ref :>> outputs =  ('CDT_System Project'::'CDT_System'::'System Analysis'::'System Functions'::'Root System Function'.'Enable Secure Collection'.'outSensor Ready'); 
                         
                    }  
                    action 'Place on Helmet' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inReady to put on Helmut' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outHead ' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Place on Helmet'.'inReady to put on Helmut'); 
                        ref :>> outputs =  ('CDT_System Project'::'CDT_System'::'System Analysis'::'System Functions'::'Root System Function'.'Place on Helmet'.'outHead '); 
                         
                    }  
                    action 'Device' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                         
                    }  
                    action 'Provide ID Information' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outDevice ID ' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'System Analysis'::'System Functions'::'Root System Function'.'Provide ID Information'.'outDevice ID '); 
                         
                    }  
                    action 'Athlete Particpates in Activity' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outActivity' : FunctionOutputPort  { 
                            attribute :>> isControlType = false; 
                            attribute :>> ordering = ObjectNodeOrderingKind::FIFO; 
                            attribute :>> isControl = false; 
                            attribute :>> kindOfNode = ObjectNodeKind::Unspecified; 
                            ref :>> outgoingExchangeItems =  ('CDT_System Project'::'CDT_System'::'Operational Analysis'::'Data'::'Hit'); 
                        }  
                        ref :>> outputs =  ('CDT_System Project'::'CDT_System'::'System Analysis'::'System Functions'::'Root System Function'.'Athlete Particpates in Activity'.'outActivity'); 
                         
                    }  
                    action 'Yield to Evaluation' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAlert' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outEvaluation' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Yield to Evaluation'.'inAlert'); 
                        ref :>> outputs =  ('CDT_System Project'::'CDT_System'::'System Analysis'::'System Functions'::'Root System Function'.'Yield to Evaluation'.'outEvaluation'); 
                         
                    }  
                    action 'Receive Athlete ' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inHead ' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outHelmut Motion' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Receive Athlete '.'inHead '); 
                        ref :>> outputs =  ('CDT_System Project'::'CDT_System'::'System Analysis'::'System Functions'::'Root System Function'.'Receive Athlete '.'outHelmut Motion'); 
                         
                    }  
                    action 'Data is Retrieved' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inEvaluation' : FunctionInputPort  { 
                            attribute :>> isControlType = false; 
                            attribute :>> ordering = ObjectNodeOrderingKind::FIFO; 
                            attribute :>> isControl = false; 
                            attribute :>> kindOfNode = ObjectNodeKind::Unspecified; 
                        }  
                        in port 'inStored Data' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outRecorded Data' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Data is Retrieved'.'inEvaluation',
                        'CDT_System Project'::'CDT_System'::'System Analysis'::'System Functions'::'Root System Function'.'Data is Retrieved'.'inStored Data'); 
                        ref :>> outputs =  ('CDT_System Project'::'CDT_System'::'System Analysis'::'System Functions'::'Root System Function'.'Data is Retrieved'.'outRecorded Data'); 
                         
                    }  
                    action 'Enable Monitoring' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSensor Ready' : FunctionInputPort  { 
                            attribute :>> isControlType = false; 
                            attribute :>> ordering = ObjectNodeOrderingKind::FIFO; 
                            attribute :>> isControl = false; 
                            attribute :>> kindOfNode = ObjectNodeKind::Unspecified; 
                        }  
                        in port 'inHelmut Motion' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outEnable Signal' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Enable Monitoring'.'inSensor Ready',
                        'CDT_System Project'::'CDT_System'::'System Analysis'::'System Functions'::'Root System Function'.'Enable Monitoring'.'inHelmut Motion'); 
                        ref :>> outputs =  ('CDT_System Project'::'CDT_System'::'System Analysis'::'System Functions'::'Root System Function'.'Enable Monitoring'.'outEnable Signal'); 
                         
                    }  
                    action 'Recieve Enabled Signal from Athelete Helmet' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inEnable Signal' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Recieve Enabled Signal from Athelete Helmet'.'inEnable Signal'); 
                         
                    }  
                    action 'Data stored' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inRecorded Data' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outStored Data ' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Data stored'.'inRecorded Data'); 
                        ref :>> outputs =  ('CDT_System Project'::'CDT_System'::'System Analysis'::'System Functions'::'Root System Function'.'Data stored'.'outStored Data '); 
                         
                    }  
                    action 'Data can be reviewed' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inStored Data ' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outInteraction 26' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Data can be reviewed'.'inStored Data '); 
                        ref :>> outputs =  ('CDT_System Project'::'CDT_System'::'System Analysis'::'System Functions'::'Root System Function'.'Data can be reviewed'.'outInteraction 26'); 
                         
                    }  
                    action 'Report Received' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inInstition Report' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Report Received'.'inInstition Report'); 
                         
                    }  
                    action 'Report Received' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete Report' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Report Received'.'inAthlete Report'); 
                         
                    }  
                    action 'Report received' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inParen Report' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Report received'.'inParen Report'); 
                         
                    }  
                    action 'Executes Policies' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inInteraction 26' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outExecute Policy' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Executes Policies'.'inInteraction 26'); 
                        ref :>> outputs =  ('CDT_System Project'::'CDT_System'::'System Analysis'::'System Functions'::'Root System Function'.'Executes Policies'.'outExecute Policy'); 
                         
                    }  
                    action 'Established Concussion Policy' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem ' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outConcussion Policy' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Established Concussion Policy'.'inSystem '); 
                        ref :>> outputs =  ('CDT_System Project'::'CDT_System'::'System Analysis'::'System Functions'::'Root System Function'.'Established Concussion Policy'.'outConcussion Policy'); 
                         
                    }  
                    action 'Generates Reports' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inExecute Policy' : FunctionInputPort  { 
                            attribute :>> isControlType = false; 
                            attribute :>> ordering = ObjectNodeOrderingKind::FIFO; 
                            attribute :>> isControl = false; 
                            attribute :>> kindOfNode = ObjectNodeKind::Unspecified; 
                        }  
                        out port 'outAthlete Report' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outInstition Report' : FunctionOutputPort  { 
                            attribute :>> isControlType = false; 
                            attribute :>> ordering = ObjectNodeOrderingKind::FIFO; 
                            attribute :>> isControl = false; 
                            attribute :>> kindOfNode = ObjectNodeKind::Unspecified; 
                        }  
                        out port 'outParen Report' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Generates Reports'.'inExecute Policy'); 
                        ref :>> outputs =  ('CDT_System Project'::'CDT_System'::'System Analysis'::'System Functions'::'Root System Function'.'Generates Reports'.'outAthlete Report',
                        'CDT_System Project'::'CDT_System'::'System Analysis'::'System Functions'::'Root System Function'.'Generates Reports'.'outInstition Report',
                        'CDT_System Project'::'CDT_System'::'System Analysis'::'System Functions'::'Root System Function'.'Generates Reports'.'outParen Report'); 
                         
                    }  
                    action 'Helmet Receives a Hit' : SystemFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inActivity' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Hit'); 
                        }  
                        out port 'outHit' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'System Analysis'::'System Functions'::'Root System Function'.'Helmet Receives a Hit'.'inActivity'); 
                        ref :>> outputs =  ('CDT_System Project'::'CDT_System'::'System Analysis'::'System Functions'::'Root System Function'.'Helmet Receives a Hit'.'outHit'); 
                         
                    }  
                    interface 'de8b39b3-0ed2-4782-9277-3264208881a2' : FunctionalExchange 
                        connect source ::> 'CDT_System Project'::'CDT_System'::'System Analysis'::'System Functions'::'Root System Function'.'Aquire System'.'outSystem'
                        to target ::> 'CDT_System Project'::'CDT_System'::'System Analysis'::'System Functions'::'Root System Function'.'Create profiles for Athletes'.'inSystem' { 
                        attribute :>> isMulticast = false; 
                        attribute :>> kindOfRate = RateKind::Unspecified; 
                        attribute :>> isMultireceive = false; 
                        attribute :>> interfaceName = "System"; 
                         
                    }  
                    interface '81872115-c1ba-45b2-b08b-7ca26e291be6' : FunctionalExchange 
                        connect source ::> 'CDT_System Project'::'CDT_System'::'System Analysis'::'System Functions'::'Root System Function'.'Provide Data for Profile'.'outAthlete Data'
                        to target ::> 'CDT_System Project'::'CDT_System'::'System Analysis'::'System Functions'::'Root System Function'.'Create profiles for Athletes'.'inAthlete Data' { 
                        attribute :>> isMulticast = false; 
                        attribute :>> kindOfRate = RateKind::Unspecified; 
                        attribute :>> isMultireceive = false; 
                        attribute :>> interfaceName = "Athlete Data"; 
                         
                    }  
                    interface 'ac6779e2-d2e5-4c8f-a9f8-079d22bd999b' : FunctionalExchange 
                        connect source ::> 'CDT_System Project'::'CDT_System'::'System Analysis'::'System Functions'::'Root System Function'.'Create profiles for Athletes'.'outProfile Data'
                        to target ::> 'CDT_System Project'::'CDT_System'::'System Analysis'::'System Functions'::'Root System Function'.'Create Unique IDs'.'inProfile Data' { 
                        attribute :>> isMulticast = false; 
                        attribute :>> kindOfRate = RateKind::Unspecified; 
                        attribute :>> isMultireceive = false; 
                        attribute :>> interfaceName = "Profile Data"; 
                         
                    }  
                    interface '9388b363-5c8b-40de-a48b-7e6d568d8924' : FunctionalExchange 
                        connect source ::> 'CDT_System Project'::'CDT_System'::'System Analysis'::'System Functions'::'Root System Function'.'Create Unique IDs'.'outID'
                        to target ::> 'CDT_System Project'::'CDT_System'::'System Analysis'::'System Functions'::'Root System Function'.'Create Unique IDs for Athlete'.'inID' { 
                        attribute :>> isMulticast = false; 
                        attribute :>> kindOfRate = RateKind::Unspecified; 
                        attribute :>> isMultireceive = false; 
                        attribute :>> interfaceName = "ID"; 
                         
                    }  
                    interface '3f53ac60-d0be-4996-a20c-2b17947a37f5' : FunctionalExchange 
                        connect source ::> 'CDT_System Project'::'CDT_System'::'System Analysis'::'System Functions'::'Root System Function'.'Create profiles for Athletes'.'outAthlete Profile'
                        to target ::> 'CDT_System Project'::'CDT_System'::'System Analysis'::'System Functions'::'Root System Function'.'Store Profile'.'inAthlete Profile' { 
                        attribute :>> isMulticast = false; 
                        attribute :>> kindOfRate = RateKind::Unspecified; 
                        attribute :>> isMultireceive = false; 
                        attribute :>> interfaceName = "Athlete Profile"; 
                         
                    }  
                    interface 'becfa74a-3f15-42a2-8c68-e36035328abf' : FunctionalExchange 
                        connect source ::> 'CDT_System Project'::'CDT_System'::'System Analysis'::'System Functions'::'Root System Function'.'Provide ID to Athlete'.'outID Card'
                        to target ::> 'CDT_System Project'::'CDT_System'::'System Analysis'::'System Functions'::'Root System Function'.'Recieve ID'.'inID Card' { 
                        attribute :>> isMulticast = false; 
                        attribute :>> kindOfRate = RateKind::Unspecified; 
                        attribute :>> isMultireceive = false; 
                        attribute :>> interfaceName = "ID Card"; 
                         
                    }  
                    interface 'd8819812-ceb3-4e0f-82f3-e5ea786c3213' : FunctionalExchange 
                        connect source ::> 'CDT_System Project'::'CDT_System'::'System Analysis'::'System Functions'::'Root System Function'.'Create Unique IDs for Athlete'.'outID Device'
                        to target ::> 'CDT_System Project'::'CDT_System'::'System Analysis'::'System Functions'::'Root System Function'.'Provide ID to Athlete'.'inID Device' { 
                        attribute :>> isMulticast = false; 
                        attribute :>> kindOfRate = RateKind::Unspecified; 
                        attribute :>> isMultireceive = false; 
                        attribute :>> interfaceName = "ID Device"; 
                         
                    }  
                    interface '6e077666-2c4b-4b4f-bc52-f3c820eb640d' : FunctionalExchange 
                        connect source ::> 'CDT_System Project'::'CDT_System'::'System Analysis'::'System Functions'::'Root System Function'.'Aquire System'.'outSystem'
                        to target ::> 'CDT_System Project'::'CDT_System'::'System Analysis'::'System Functions'::'Root System Function'.'Assemble System Components'.'inSystem' { 
                        attribute :>> isMulticast = false; 
                        attribute :>> kindOfRate = RateKind::Unspecified; 
                        attribute :>> isMultireceive = false; 
                        attribute :>> interfaceName = "System"; 
                         
                    }  
                    interface 'db063bdb-25e6-4b61-8fa6-8afa652d070e' : FunctionalExchange 
                        connect source ::> 'CDT_System Project'::'CDT_System'::'System Analysis'::'System Functions'::'Root System Function'.'Provide access to helmut mounting'.'outhelmut mounting'
                        to target ::> 'CDT_System Project'::'CDT_System'::'System Analysis'::'System Functions'::'Root System Function'.'Assemble System Components'.'inhelmut mounting' { 
                        attribute :>> isMulticast = false; 
                        attribute :>> kindOfRate = RateKind::Unspecified; 
                        attribute :>> isMultireceive = false; 
                        attribute :>> interfaceName = "helmet mounting"; 
                         
                    }  
                    interface '54af6de5-a1e2-4873-9717-47cae6371e49' : FunctionalExchange 
                        connect source ::> 'CDT_System Project'::'CDT_System'::'System Analysis'::'System Functions'::'Root System Function'.'Recieve ID'.'outAthlete ID'
                        to target ::> 'CDT_System Project'::'CDT_System'::'System Analysis'::'System Functions'::'Root System Function'.'Enable Secure Collection'.'inAthlete ID' { 
                        attribute :>> isMulticast = false; 
                        attribute :>> kindOfRate = RateKind::Unspecified; 
                        attribute :>> isMultireceive = false; 
                        attribute :>> interfaceName = "Athlete ID"; 
                         
                    }  
                    interface '45d4d189-5015-411b-8a8d-d304a60b8cc5' : FunctionalExchange 
                        connect source ::> 'CDT_System Project'::'CDT_System'::'System Analysis'::'System Functions'::'Root System Function'.'Provide access to sensing device mounting'.'outsensor mounting'
                        to target ::> 'CDT_System Project'::'CDT_System'::'System Analysis'::'System Functions'::'Root System Function'.'Assemble System Components'.'insensor mounting' { 
                        attribute :>> isMulticast = false; 
                        attribute :>> kindOfRate = RateKind::Unspecified; 
                        attribute :>> isMultireceive = false; 
                        attribute :>> interfaceName = "sensor mounting"; 
                         
                    }  
                    interface '4b7db120-066b-471e-a1f8-3687241321b1' : FunctionalExchange 
                        connect source ::> 'CDT_System Project'::'CDT_System'::'System Analysis'::'System Functions'::'Root System Function'.'Assemble System Components'.'outAssembled System'
                        to target ::> 'CDT_System Project'::'CDT_System'::'System Analysis'::'System Functions'::'Root System Function'.'Prep the device for use'.'inAssembled System' { 
                        attribute :>> isMulticast = false; 
                        attribute :>> kindOfRate = RateKind::Unspecified; 
                        attribute :>> isMultireceive = false; 
                        attribute :>> interfaceName = "Assembled System"; 
                         
                    }  
                    interface '96aa037f-ec86-482c-abbc-444ca7fef501' : FunctionalExchange 
                        connect source ::> 'CDT_System Project'::'CDT_System'::'System Analysis'::'System Functions'::'Root System Function'.'Recieve ID'.'outID'
                        to target ::> 'CDT_System Project'::'CDT_System'::'System Analysis'::'System Functions'::'Root System Function'.'Insert ID into Sensing Device'.'inID' { 
                        attribute :>> isMulticast = false; 
                        attribute :>> kindOfRate = RateKind::Unspecified; 
                        attribute :>> isMultireceive = false; 
                        attribute :>> interfaceName = "ID"; 
                         
                    }  
                    interface '6aaff874-bc5c-4b3a-8750-2b5cb9ffa876' : FunctionalExchange 
                        connect source ::> 'CDT_System Project'::'CDT_System'::'System Analysis'::'System Functions'::'Root System Function'.'Insert ID into Sensing Device'.'outID'
                        to target ::> 'CDT_System Project'::'CDT_System'::'System Analysis'::'System Functions'::'Root System Function'.'Recieve ID'.'inID' { 
                        attribute :>> isMulticast = false; 
                        attribute :>> kindOfRate = RateKind::Unspecified; 
                        attribute :>> isMultireceive = false; 
                        attribute :>> interfaceName = "ID"; 
                         
                    }  
                    interface 'd2aa068f-0d8a-43cf-95af-f9db099ebadf' : FunctionalExchange 
                        connect source ::> 'CDT_System Project'::'CDT_System'::'System Analysis'::'System Functions'::'Root System Function'.'Receive Athlete '.'outHelmut Motion'
                        to target ::> 'CDT_System Project'::'CDT_System'::'System Analysis'::'System Functions'::'Root System Function'.'Enable Monitoring'.'inHelmut Motion' { 
                        attribute :>> isMulticast = false; 
                        attribute :>> kindOfRate = RateKind::Unspecified; 
                        attribute :>> isMultireceive = false; 
                        attribute :>> interfaceName = "Helmet Motion"; 
                         
                    }  
                    interface '7e3bc9a2-7ee0-4b84-b6a5-cb7b56fd966f' : FunctionalExchange 
                        connect source ::> 'CDT_System Project'::'CDT_System'::'System Analysis'::'System Functions'::'Root System Function'.'Place on Helmet'.'outHead '
                        to target ::> 'CDT_System Project'::'CDT_System'::'System Analysis'::'System Functions'::'Root System Function'.'Receive Athlete '.'inHead ' { 
                        attribute :>> isMulticast = false; 
                        attribute :>> kindOfRate = RateKind::Unspecified; 
                        attribute :>> isMultireceive = false; 
                        attribute :>> interfaceName = "Head "; 
                         
                    }  
                    interface 'db4f5ed3-3d7e-487a-b098-8da26c258ffa' : FunctionalExchange 
                        connect source ::> 'CDT_System Project'::'CDT_System'::'System Analysis'::'System Functions'::'Root System Function'.'Data is Retrieved'.'outRecorded Data'
                        to target ::> 'CDT_System Project'::'CDT_System'::'System Analysis'::'System Functions'::'Root System Function'.'Data stored'.'inRecorded Data' { 
                        attribute :>> isMulticast = false; 
                        attribute :>> kindOfRate = RateKind::Unspecified; 
                        attribute :>> isMultireceive = false; 
                        attribute :>> interfaceName = "Recorded Data"; 
                         
                    }  
                    interface '317c24bc-f488-4511-8223-4876ad934caf' : FunctionalExchange 
                        connect source ::> 'CDT_System Project'::'CDT_System'::'System Analysis'::'System Functions'::'Root System Function'.'Data stored'.'outStored Data '
                        to target ::> 'CDT_System Project'::'CDT_System'::'System Analysis'::'System Functions'::'Root System Function'.'Data can be reviewed'.'inStored Data ' { 
                        attribute :>> isMulticast = false; 
                        attribute :>> kindOfRate = RateKind::Unspecified; 
                        attribute :>> isMultireceive = false; 
                        attribute :>> interfaceName = "Stored Data "; 
                         
                    }  
                    interface '1e684e43-60e9-4843-a5b4-53e1b3956172' : FunctionalExchange 
                        connect source ::> 'CDT_System Project'::'CDT_System'::'System Analysis'::'System Functions'::'Root System Function'.'Data can be reviewed'.'outInteraction 26'
                        to target ::> 'CDT_System Project'::'CDT_System'::'System Analysis'::'System Functions'::'Root System Function'.'Executes Policies'.'inInteraction 26' { 
                        attribute :>> isMulticast = false; 
                        attribute :>> kindOfRate = RateKind::Unspecified; 
                        attribute :>> isMultireceive = false; 
                        attribute :>> interfaceName = "Interaction 26"; 
                         
                    }  
                    interface '9b048ee7-bda2-4dfc-965a-74f634201071' : FunctionalExchange 
                        connect source ::> 'CDT_System Project'::'CDT_System'::'System Analysis'::'System Functions'::'Root System Function'.'Aquire System'.'outSystem '
                        to target ::> 'CDT_System Project'::'CDT_System'::'System Analysis'::'System Functions'::'Root System Function'.'Established Concussion Policy'.'inSystem ' { 
                        attribute :>> isMulticast = false; 
                        attribute :>> kindOfRate = RateKind::Unspecified; 
                        attribute :>> isMultireceive = false; 
                        attribute :>> interfaceName = "System "; 
                         
                    }  
                    interface 'e3537a0e-76e0-4fe8-897b-f1feb95dcfd2' : FunctionalExchange 
                        connect source ::> 'CDT_System Project'::'CDT_System'::'System Analysis'::'System Functions'::'Root System Function'.'Established Concussion Policy'.'outConcussion Policy'
                        to target ::> 'CDT_System Project'::'CDT_System'::'System Analysis'::'System Functions'::'Root System Function'.'Trainer Recieves Concussion Alert'.'inConcussion Policy' { 
                        attribute :>> isMulticast = false; 
                        attribute :>> kindOfRate = RateKind::Unspecified; 
                        attribute :>> isMultireceive = false; 
                        attribute :>> interfaceName = "Concussion Policy"; 
                         
                    }  
                    interface '65231319-835b-4eac-8173-8c7bd196f040' : FunctionalExchange 
                        connect source ::> 'CDT_System Project'::'CDT_System'::'System Analysis'::'System Functions'::'Root System Function'.'Provide ID Information'.'outDevice ID '
                        to target ::> 'CDT_System Project'::'CDT_System'::'System Analysis'::'System Functions'::'Root System Function'.'Enable Secure Collection'.'inDevice ID ' { 
                        attribute :>> isMulticast = false; 
                        attribute :>> kindOfRate = RateKind::Unspecified; 
                        attribute :>> isMultireceive = false; 
                        attribute :>> interfaceName = "Device ID "; 
                         
                    }  
                    interface '68cb347a-561b-4144-a0e2-4e88d7e29875' : FunctionalExchange 
                        connect source ::> 'CDT_System Project'::'CDT_System'::'System Analysis'::'System Functions'::'Root System Function'.'Executes Policies'.'outExecute Policy'
                        to target ::> 'CDT_System Project'::'CDT_System'::'System Analysis'::'System Functions'::'Root System Function'.'Generates Reports'.'inExecute Policy' { 
                        attribute :>> isMulticast = false; 
                        attribute :>> kindOfRate = RateKind::Unspecified; 
                        attribute :>> isMultireceive = false; 
                        attribute :>> interfaceName = "Execute Policy"; 
                         
                        ref :>> exchangedItems =  ('CDT_System Project'::'CDT_System'::'Operational Analysis'::'Data'::'Policy'); 
                    }  
                    interface 'ccadc84d-edde-4250-9bde-a78ae466fbad' : FunctionalExchange 
                        connect source ::> 'CDT_System Project'::'CDT_System'::'System Analysis'::'System Functions'::'Root System Function'.'Trainer Recieves Concussion Alert'.'outAlert'
                        to target ::> 'CDT_System Project'::'CDT_System'::'System Analysis'::'System Functions'::'Root System Function'.'Yield to Evaluation'.'inAlert' { 
                        attribute :>> isMulticast = false; 
                        attribute :>> kindOfRate = RateKind::Unspecified; 
                        attribute :>> isMultireceive = false; 
                        attribute :>> interfaceName = "Alert"; 
                         
                    }  
                    interface '7f0a842b-0f47-4a50-98b8-4116a4ed43c8' : FunctionalExchange 
                        connect source ::> 'CDT_System Project'::'CDT_System'::'System Analysis'::'System Functions'::'Root System Function'.'Generates Reports'.'outAthlete Report'
                        to target ::> 'CDT_System Project'::'CDT_System'::'System Analysis'::'System Functions'::'Root System Function'.'Report Received'.'inAthlete Report' { 
                        attribute :>> isMulticast = false; 
                        attribute :>> kindOfRate = RateKind::Unspecified; 
                        attribute :>> isMultireceive = false; 
                        attribute :>> interfaceName = "Athlete Report"; 
                         
                        ref :>> exchangedItems =  ('CDT_System Project'::'CDT_System'::'Operational Analysis'::'Data'::'Report'); 
                    }  
                    interface '63588dfa-f2f9-4eb4-93de-72bac38f5fc2' : FunctionalExchange 
                        connect source ::> 'CDT_System Project'::'CDT_System'::'System Analysis'::'System Functions'::'Root System Function'.'Enable Secure Collection'.'outSensor Ready'
                        to target ::> 'CDT_System Project'::'CDT_System'::'System Analysis'::'System Functions'::'Root System Function'.'Enable Monitoring'.'inSensor Ready' { 
                        attribute :>> isMulticast = false; 
                        attribute :>> kindOfRate = RateKind::Unspecified; 
                        attribute :>> isMultireceive = false; 
                        attribute :>> interfaceName = "Sensor Ready"; 
                         
                    }  
                    interface '0a7f17b0-3306-4d7a-8196-b6a4818100ac' : FunctionalExchange 
                        connect source ::> 'CDT_System Project'::'CDT_System'::'System Analysis'::'System Functions'::'Root System Function'.'Enable Monitoring'.'outEnable Signal'
                        to target ::> 'CDT_System Project'::'CDT_System'::'System Analysis'::'System Functions'::'Root System Function'.'Recieve Enabled Signal from Athelete Helmet'.'inEnable Signal' { 
                        attribute :>> isMulticast = false; 
                        attribute :>> kindOfRate = RateKind::Unspecified; 
                        attribute :>> isMultireceive = false; 
                        attribute :>> interfaceName = "Enable Signal"; 
                         
                    }  
                    interface '64ccd66f-c036-4a8e-89f0-88294cf921ff' : FunctionalExchange 
                        connect source ::> 'CDT_System Project'::'CDT_System'::'System Analysis'::'System Functions'::'Root System Function'.'Insert ID into Sensing Device'.'outReady to put on Helmut'
                        to target ::> 'CDT_System Project'::'CDT_System'::'System Analysis'::'System Functions'::'Root System Function'.'Place on Helmet'.'inReady to put on Helmut' { 
                        attribute :>> isMulticast = false; 
                        attribute :>> kindOfRate = RateKind::Unspecified; 
                        attribute :>> isMultireceive = false; 
                        attribute :>> interfaceName = "Ready to put on Helmet"; 
                         
                    }  
                    interface '6067b5d5-fbf6-466c-ab48-87c045004339' : FunctionalExchange 
                        connect source ::> 'CDT_System Project'::'CDT_System'::'System Analysis'::'System Functions'::'Root System Function'.'Generates Reports'.'outInstition Report'
                        to target ::> 'CDT_System Project'::'CDT_System'::'System Analysis'::'System Functions'::'Root System Function'.'Report Received'.'inInstition Report' { 
                        attribute :>> isMulticast = false; 
                        attribute :>> kindOfRate = RateKind::Unspecified; 
                        attribute :>> isMultireceive = false; 
                        attribute :>> interfaceName = "Instition Report"; 
                         
                        ref :>> exchangedItems =  ('CDT_System Project'::'CDT_System'::'Operational Analysis'::'Data'::'Report'); 
                    }  
                    interface '807a6b94-cf3b-47d4-b41c-036867b29a84' : FunctionalExchange 
                        connect source ::> 'CDT_System Project'::'CDT_System'::'System Analysis'::'System Functions'::'Root System Function'.'Generates Reports'.'outParen Report'
                        to target ::> 'CDT_System Project'::'CDT_System'::'System Analysis'::'System Functions'::'Root System Function'.'Report received'.'inParen Report' { 
                        attribute :>> isMulticast = false; 
                        attribute :>> kindOfRate = RateKind::Unspecified; 
                        attribute :>> isMultireceive = false; 
                        attribute :>> interfaceName = "Paren Report"; 
                         
                        ref :>> exchangedItems =  ('CDT_System Project'::'CDT_System'::'Operational Analysis'::'Data'::'Report'); 
                    }  
                    interface 'fcbc8312-6fba-41cd-b0ff-caf04d9dced8' : FunctionalExchange 
                        connect source ::> 'CDT_System Project'::'CDT_System'::'System Analysis'::'System Functions'::'Root System Function'.'Yield to Evaluation'.'outEvaluation'
                        to target ::> 'CDT_System Project'::'CDT_System'::'System Analysis'::'System Functions'::'Root System Function'.'Data is Retrieved'.'inEvaluation' { 
                        attribute :>> isMulticast = false; 
                        attribute :>> kindOfRate = RateKind::Unspecified; 
                        attribute :>> isMultireceive = false; 
                        attribute :>> interfaceName = "Evaluation"; 
                         
                    }  
                    interface '8520e06a-fe44-4659-8276-5a2d135f9211' : FunctionalExchange 
                        connect source ::> 'CDT_System Project'::'CDT_System'::'System Analysis'::'System Functions'::'Root System Function'.'Device alerts possible Concussion'.'outConcussion Alert to Trainer'
                        to target ::> 'CDT_System Project'::'CDT_System'::'System Analysis'::'System Functions'::'Root System Function'.'Trainer Recieves Concussion Alert'.'inConcussion Alert to Trainer' { 
                        attribute :>> isMulticast = false; 
                        attribute :>> kindOfRate = RateKind::Unspecified; 
                        attribute :>> isMultireceive = false; 
                        attribute :>> interfaceName = "Concussion Alert to Trainer"; 
                         
                        ref :>> exchangedItems =  ('CDT_System Project'::'CDT_System'::'Operational Analysis'::'Data'::'Alert'); 
                    }  
                    interface '97a72935-6d79-46ff-b4b7-1d130ca15b47' : FunctionalExchange 
                        connect source ::> 'CDT_System Project'::'CDT_System'::'System Analysis'::'System Functions'::'Root System Function'.'Athlete Particpates in Activity'.'outActivity'
                        to target ::> 'CDT_System Project'::'CDT_System'::'System Analysis'::'System Functions'::'Root System Function'.'Helmet Receives a Hit'.'inActivity' { 
                        attribute :>> isMulticast = false; 
                        attribute :>> kindOfRate = RateKind::Unspecified; 
                        attribute :>> isMultireceive = false; 
                        attribute :>> interfaceName = "Activity"; 
                         
                        ref :>> exchangedItems =  ('CDT_System Project'::'CDT_System'::'Operational Analysis'::'Data'::'Hit'); 
                    }  
                    interface '12f0e27a-cfda-4d15-acc7-c343637f5dee' : FunctionalExchange 
                        connect source ::> 'CDT_System Project'::'CDT_System'::'System Analysis'::'System Functions'::'Root System Function'.'Helmet Receives a Hit'.'outHit'
                        to target ::> 'CDT_System Project'::'CDT_System'::'System Analysis'::'System Functions'::'Root System Function'.'Device records Hit'.'inHit' { 
                        attribute :>> isMulticast = false; 
                        attribute :>> kindOfRate = RateKind::Unspecified; 
                        attribute :>> isMultireceive = false; 
                        attribute :>> interfaceName = "Hit"; 
                         
                        ref :>> exchangedItems =  ('CDT_System Project'::'CDT_System'::'Operational Analysis'::'Data'::'Hit'); 
                    }  
                    interface '4b9c774c-e9a5-431a-ad18-2f8690985890' : FunctionalExchange 
                        connect source ::> 'CDT_System Project'::'CDT_System'::'System Analysis'::'System Functions'::'Root System Function'.'Device records Hit'.'outConcussion'
                        to target ::> 'CDT_System Project'::'CDT_System'::'System Analysis'::'System Functions'::'Root System Function'.'Device alerts possible Concussion'.'inConcussion' { 
                        attribute :>> isMulticast = false; 
                        attribute :>> kindOfRate = RateKind::Unspecified; 
                        attribute :>> isMultireceive = false; 
                        attribute :>> interfaceName = "Concussion"; 
                         
                    }  
                    interface 'f3c6d7e4-fef4-45a0-ac16-8f3392ce7aed' : FunctionalExchange 
                        connect source ::> 'CDT_System Project'::'CDT_System'::'System Analysis'::'System Functions'::'Root System Function'.'Device records Hit'.'outStored Data'
                        to target ::> 'CDT_System Project'::'CDT_System'::'System Analysis'::'System Functions'::'Root System Function'.'Data is Retrieved'.'inStored Data' { 
                        attribute :>> isMulticast = false; 
                        attribute :>> kindOfRate = RateKind::Unspecified; 
                        attribute :>> isMultireceive = false; 
                        attribute :>> interfaceName = "Stored Data"; 
                         
                    }  
                     
                    ref :>> ownedFunctions =  ('CDT_System Project'::'CDT_System'::'System Analysis'::'System Functions'::'Root System Function'.'Aquire System',
                    'CDT_System Project'::'CDT_System'::'System Analysis'::'System Functions'::'Root System Function'.'Create profiles for Athletes',
                    'CDT_System Project'::'CDT_System'::'System Analysis'::'System Functions'::'Root System Function'.'Create Unique IDs for Athlete',
                    'CDT_System Project'::'CDT_System'::'System Analysis'::'System Functions'::'Root System Function'.'Provide Data for Profile',
                    'CDT_System Project'::'CDT_System'::'System Analysis'::'System Functions'::'Root System Function'.'Recieve ID',
                    'CDT_System Project'::'CDT_System'::'System Analysis'::'System Functions'::'Root System Function'.'Store Profile',
                    'CDT_System Project'::'CDT_System'::'System Analysis'::'System Functions'::'Root System Function'.'Create Unique IDs',
                    'CDT_System Project'::'CDT_System'::'System Analysis'::'System Functions'::'Root System Function'.'Provide ID to Athlete',
                    'CDT_System Project'::'CDT_System'::'System Analysis'::'System Functions'::'Root System Function'.'Assemble System Components',
                    'CDT_System Project'::'CDT_System'::'System Analysis'::'System Functions'::'Root System Function'.'Provide access to helmut mounting',
                    'CDT_System Project'::'CDT_System'::'System Analysis'::'System Functions'::'Root System Function'.'Provide access to sensing device mounting',
                    'CDT_System Project'::'CDT_System'::'System Analysis'::'System Functions'::'Root System Function'.'Prep the device for use',
                    'CDT_System Project'::'CDT_System'::'System Analysis'::'System Functions'::'Root System Function'.'Insert ID into Sensing Device',
                    'CDT_System Project'::'CDT_System'::'System Analysis'::'System Functions'::'Root System Function'.'Recieve ID',
                    'CDT_System Project'::'CDT_System'::'System Analysis'::'System Functions'::'Root System Function'.'Device alerts possible Concussion',
                    'CDT_System Project'::'CDT_System'::'System Analysis'::'System Functions'::'Root System Function'.'Trainer Recieves Concussion Alert',
                    'CDT_System Project'::'CDT_System'::'System Analysis'::'System Functions'::'Root System Function'.'Device records Hit',
                    'CDT_System Project'::'CDT_System'::'System Analysis'::'System Functions'::'Root System Function'.'Enable Secure Collection',
                    'CDT_System Project'::'CDT_System'::'System Analysis'::'System Functions'::'Root System Function'.'Place on Helmet',
                    'CDT_System Project'::'CDT_System'::'System Analysis'::'System Functions'::'Root System Function'.'Device',
                    'CDT_System Project'::'CDT_System'::'System Analysis'::'System Functions'::'Root System Function'.'Provide ID Information',
                    'CDT_System Project'::'CDT_System'::'System Analysis'::'System Functions'::'Root System Function'.'Athlete Particpates in Activity',
                    'CDT_System Project'::'CDT_System'::'System Analysis'::'System Functions'::'Root System Function'.'Yield to Evaluation',
                    'CDT_System Project'::'CDT_System'::'System Analysis'::'System Functions'::'Root System Function'.'Receive Athlete ',
                    'CDT_System Project'::'CDT_System'::'System Analysis'::'System Functions'::'Root System Function'.'Data is Retrieved',
                    'CDT_System Project'::'CDT_System'::'System Analysis'::'System Functions'::'Root System Function'.'Enable Monitoring',
                    'CDT_System Project'::'CDT_System'::'System Analysis'::'System Functions'::'Root System Function'.'Recieve Enabled Signal from Athelete Helmet',
                    'CDT_System Project'::'CDT_System'::'System Analysis'::'System Functions'::'Root System Function'.'Data stored',
                    'CDT_System Project'::'CDT_System'::'System Analysis'::'System Functions'::'Root System Function'.'Data can be reviewed',
                    'CDT_System Project'::'CDT_System'::'System Analysis'::'System Functions'::'Root System Function'.'Report Received',
                    'CDT_System Project'::'CDT_System'::'System Analysis'::'System Functions'::'Root System Function'.'Report Received',
                    'CDT_System Project'::'CDT_System'::'System Analysis'::'System Functions'::'Root System Function'.'Report received',
                    'CDT_System Project'::'CDT_System'::'System Analysis'::'System Functions'::'Root System Function'.'Executes Policies',
                    'CDT_System Project'::'CDT_System'::'System Analysis'::'System Functions'::'Root System Function'.'Established Concussion Policy',
                    'CDT_System Project'::'CDT_System'::'System Analysis'::'System Functions'::'Root System Function'.'Generates Reports',
                    'CDT_System Project'::'CDT_System'::'System Analysis'::'System Functions'::'Root System Function'.'Helmet Receives a Hit'); 
                     
                    ref :>> ownedFunctionalExchanges =  ('CDT_System Project'::'CDT_System'::'System Analysis'::'System Functions'::'Root System Function'.'de8b39b3-0ed2-4782-9277-3264208881a2',
                    'CDT_System Project'::'CDT_System'::'System Analysis'::'System Functions'::'Root System Function'.'81872115-c1ba-45b2-b08b-7ca26e291be6',
                    'CDT_System Project'::'CDT_System'::'System Analysis'::'System Functions'::'Root System Function'.'ac6779e2-d2e5-4c8f-a9f8-079d22bd999b',
                    'CDT_System Project'::'CDT_System'::'System Analysis'::'System Functions'::'Root System Function'.'9388b363-5c8b-40de-a48b-7e6d568d8924',
                    'CDT_System Project'::'CDT_System'::'System Analysis'::'System Functions'::'Root System Function'.'3f53ac60-d0be-4996-a20c-2b17947a37f5',
                    'CDT_System Project'::'CDT_System'::'System Analysis'::'System Functions'::'Root System Function'.'becfa74a-3f15-42a2-8c68-e36035328abf',
                    'CDT_System Project'::'CDT_System'::'System Analysis'::'System Functions'::'Root System Function'.'d8819812-ceb3-4e0f-82f3-e5ea786c3213',
                    'CDT_System Project'::'CDT_System'::'System Analysis'::'System Functions'::'Root System Function'.'6e077666-2c4b-4b4f-bc52-f3c820eb640d',
                    'CDT_System Project'::'CDT_System'::'System Analysis'::'System Functions'::'Root System Function'.'db063bdb-25e6-4b61-8fa6-8afa652d070e',
                    'CDT_System Project'::'CDT_System'::'System Analysis'::'System Functions'::'Root System Function'.'54af6de5-a1e2-4873-9717-47cae6371e49',
                    'CDT_System Project'::'CDT_System'::'System Analysis'::'System Functions'::'Root System Function'.'45d4d189-5015-411b-8a8d-d304a60b8cc5',
                    'CDT_System Project'::'CDT_System'::'System Analysis'::'System Functions'::'Root System Function'.'4b7db120-066b-471e-a1f8-3687241321b1',
                    'CDT_System Project'::'CDT_System'::'System Analysis'::'System Functions'::'Root System Function'.'96aa037f-ec86-482c-abbc-444ca7fef501',
                    'CDT_System Project'::'CDT_System'::'System Analysis'::'System Functions'::'Root System Function'.'6aaff874-bc5c-4b3a-8750-2b5cb9ffa876',
                    'CDT_System Project'::'CDT_System'::'System Analysis'::'System Functions'::'Root System Function'.'d2aa068f-0d8a-43cf-95af-f9db099ebadf',
                    'CDT_System Project'::'CDT_System'::'System Analysis'::'System Functions'::'Root System Function'.'7e3bc9a2-7ee0-4b84-b6a5-cb7b56fd966f',
                    'CDT_System Project'::'CDT_System'::'System Analysis'::'System Functions'::'Root System Function'.'db4f5ed3-3d7e-487a-b098-8da26c258ffa',
                    'CDT_System Project'::'CDT_System'::'System Analysis'::'System Functions'::'Root System Function'.'317c24bc-f488-4511-8223-4876ad934caf',
                    'CDT_System Project'::'CDT_System'::'System Analysis'::'System Functions'::'Root System Function'.'1e684e43-60e9-4843-a5b4-53e1b3956172',
                    'CDT_System Project'::'CDT_System'::'System Analysis'::'System Functions'::'Root System Function'.'9b048ee7-bda2-4dfc-965a-74f634201071',
                    'CDT_System Project'::'CDT_System'::'System Analysis'::'System Functions'::'Root System Function'.'e3537a0e-76e0-4fe8-897b-f1feb95dcfd2',
                    'CDT_System Project'::'CDT_System'::'System Analysis'::'System Functions'::'Root System Function'.'65231319-835b-4eac-8173-8c7bd196f040',
                    'CDT_System Project'::'CDT_System'::'System Analysis'::'System Functions'::'Root System Function'.'68cb347a-561b-4144-a0e2-4e88d7e29875',
                    'CDT_System Project'::'CDT_System'::'System Analysis'::'System Functions'::'Root System Function'.'ccadc84d-edde-4250-9bde-a78ae466fbad',
                    'CDT_System Project'::'CDT_System'::'System Analysis'::'System Functions'::'Root System Function'.'7f0a842b-0f47-4a50-98b8-4116a4ed43c8',
                    'CDT_System Project'::'CDT_System'::'System Analysis'::'System Functions'::'Root System Function'.'63588dfa-f2f9-4eb4-93de-72bac38f5fc2',
                    'CDT_System Project'::'CDT_System'::'System Analysis'::'System Functions'::'Root System Function'.'0a7f17b0-3306-4d7a-8196-b6a4818100ac',
                    'CDT_System Project'::'CDT_System'::'System Analysis'::'System Functions'::'Root System Function'.'64ccd66f-c036-4a8e-89f0-88294cf921ff',
                    'CDT_System Project'::'CDT_System'::'System Analysis'::'System Functions'::'Root System Function'.'6067b5d5-fbf6-466c-ab48-87c045004339',
                    'CDT_System Project'::'CDT_System'::'System Analysis'::'System Functions'::'Root System Function'.'807a6b94-cf3b-47d4-b41c-036867b29a84',
                    'CDT_System Project'::'CDT_System'::'System Analysis'::'System Functions'::'Root System Function'.'fcbc8312-6fba-41cd-b0ff-caf04d9dced8',
                    'CDT_System Project'::'CDT_System'::'System Analysis'::'System Functions'::'Root System Function'.'8520e06a-fe44-4659-8276-5a2d135f9211',
                    'CDT_System Project'::'CDT_System'::'System Analysis'::'System Functions'::'Root System Function'.'97a72935-6d79-46ff-b4b7-1d130ca15b47',
                    'CDT_System Project'::'CDT_System'::'System Analysis'::'System Functions'::'Root System Function'.'12f0e27a-cfda-4d15-acc7-c343637f5dee',
                    'CDT_System Project'::'CDT_System'::'System Analysis'::'System Functions'::'Root System Function'.'4b9c774c-e9a5-431a-ad18-2f8690985890',
                    'CDT_System Project'::'CDT_System'::'System Analysis'::'System Functions'::'Root System Function'.'f3c6d7e4-fef4-45a0-ac16-8f3392ce7aed'); 
                }  
            } 
            package  'Interfaces' {
                @PackageMeta {
                    type = "InterfacePkg";
                } 
                item 'Hit' : InterfaceItem  { 
                    attribute :>> isStructural = true; 
                    attribute :>> isAbstract = false; 
                    attribute :>> isFinal = false; 
                    allocation '67ccc2f4-3383-452b-b394-b091417f7d27' : ExchangeItemAllocation
                        allocate allocatedItem ::> 'CDT_System Project'::'CDT_System'::'Operational Analysis'::'Data'::'Hit'
                        to allocatingInterface ::> 'CDT_System Project'::'CDT_System'::'System Analysis'::'Interfaces'::'Hit'; 
                     
                    ref :>> ownedExchangeItemAllocations =  ('CDT_System Project'::'CDT_System'::'System Analysis'::'Interfaces'::'Hit'.'67ccc2f4-3383-452b-b394-b091417f7d27'); 
                }  
                item 'Alert' : InterfaceItem  { 
                    attribute :>> isStructural = true; 
                    attribute :>> isAbstract = false; 
                    attribute :>> isFinal = false; 
                    allocation 'b038c686-671f-492a-adb1-7f4b211a6b17' : ExchangeItemAllocation
                        allocate allocatedItem ::> 'CDT_System Project'::'CDT_System'::'Operational Analysis'::'Data'::'Alert'
                        to allocatingInterface ::> 'CDT_System Project'::'CDT_System'::'System Analysis'::'Interfaces'::'Alert'; 
                     
                    ref :>> ownedExchangeItemAllocations =  ('CDT_System Project'::'CDT_System'::'System Analysis'::'Interfaces'::'Alert'.'b038c686-671f-492a-adb1-7f4b211a6b17'); 
                }  
            } 
            package  'Capabilities' {
                @PackageMeta {
                    type = "CapabilityPkg";
                } 
                use case 'Maintain Device' : Capability { 
                    actor 'CDT System' = 'CDT_System Project'::'CDT_System'::'System Analysis'::'Structure'::'CDT System'; 
                    actor 'Sensing Device' = 'CDT_System Project'::'CDT_System'::'System Analysis'::'Structure'::'Sensing Device'; 
                    actor 'Helmet' = 'CDT_System Project'::'CDT_System'::'System Analysis'::'Structure'::'Helmet'; 
                    actor 'ID Device' = 'CDT_System Project'::'CDT_System'::'System Analysis'::'Structure'::'ID Device'; 
                    actor 'Secure Cloud' = 'CDT_System Project'::'CDT_System'::'System Analysis'::'Structure'::'Secure Cloud'; 
                    actor 'Trainer' = 'CDT_System Project'::'CDT_System'::'System Analysis'::'Structure'::'Trainer'; 
                    ref action '51d155f2-7585-4f21-8562-b6b3ae844a57' = 'CDT_System Project'::'CDT_System'::'System Analysis'::'System Functions'::'Root System Function'.'Maintain'; 
                     
                     
                }  
                use case 'Aquire Device' : Capability { 
                    actor 'Instituion' = 'CDT_System Project'::'CDT_System'::'System Analysis'::'Structure'::'Instituion'; 
                    actor 'CDT System' = 'CDT_System Project'::'CDT_System'::'System Analysis'::'Structure'::'CDT System'; 
                    actor 'Trainer' = 'CDT_System Project'::'CDT_System'::'System Analysis'::'Structure'::'Trainer'; 
                    ref action '7fede00d-1643-4241-9def-b6ab3ef4cc6b' = 'CDT_System Project'::'CDT_System'::'System Analysis'::'System Functions'::'Root System Function'.'Acquire Device'; 
                     
                     
                }  
                use case 'Activate Detection' : Capability { 
                    actor 'Athlete' = 'CDT_System Project'::'CDT_System'::'System Analysis'::'Structure'::'Athlete'; 
                    actor 'ID Device' = 'CDT_System Project'::'CDT_System'::'System Analysis'::'Structure'::'ID Device'; 
                    actor 'Helmet' = 'CDT_System Project'::'CDT_System'::'System Analysis'::'Structure'::'Helmet'; 
                    actor 'Sensing Device' = 'CDT_System Project'::'CDT_System'::'System Analysis'::'Structure'::'Sensing Device'; 
                    actor 'Secure Cloud' = 'CDT_System Project'::'CDT_System'::'System Analysis'::'Structure'::'Secure Cloud'; 
                    actor 'Trainer' = 'CDT_System Project'::'CDT_System'::'System Analysis'::'Structure'::'Trainer'; 
                    ref action '2155cce5-cace-4ab3-bc6e-6ab99ca2f371' = 'CDT_System Project'::'CDT_System'::'System Analysis'::'System Functions'::'Root System Function'.'Activate Detection Device'; 
                     
                     
                }  
                use case 'Download Data' : Capability { 
                    actor 'CDT System' = 'CDT_System Project'::'CDT_System'::'System Analysis'::'Structure'::'CDT System'; 
                    actor 'Parent' = 'CDT_System Project'::'CDT_System'::'System Analysis'::'Structure'::'Parent'; 
                    actor 'Athlete' = 'CDT_System Project'::'CDT_System'::'System Analysis'::'Structure'::'Athlete'; 
                    actor 'Instituion' = 'CDT_System Project'::'CDT_System'::'System Analysis'::'Structure'::'Instituion'; 
                    actor 'Trainer' = 'CDT_System Project'::'CDT_System'::'System Analysis'::'Structure'::'Trainer'; 
                    ref action '19f6c90b-30ab-4102-b05b-e0dc1acb6cb9' = 'CDT_System Project'::'CDT_System'::'System Analysis'::'System Functions'::'Root System Function'.'Download Data'; 
                     
                     
                }  
                use case 'Detect Concussion' : Capability { 
                    actor 'Athlete' = 'CDT_System Project'::'CDT_System'::'System Analysis'::'Structure'::'Athlete'; 
                    actor 'Helmet' = 'CDT_System Project'::'CDT_System'::'System Analysis'::'Structure'::'Helmet'; 
                    actor 'Sensing Device' = 'CDT_System Project'::'CDT_System'::'System Analysis'::'Structure'::'Sensing Device'; 
                    actor 'CDT System' = 'CDT_System Project'::'CDT_System'::'System Analysis'::'Structure'::'CDT System'; 
                    actor 'Trainer' = 'CDT_System Project'::'CDT_System'::'System Analysis'::'Structure'::'Trainer'; 
                    ref action 'efdfe1cb-1ceb-435c-9a89-1f1082321306' = 'CDT_System Project'::'CDT_System'::'System Analysis'::'System Functions'::'Root System Function'.'Detect Concussion'; 
                     
                     
                     
                }  
            } 
            package  'Structure' {
                @PackageMeta {
                    type = "SystemComponentPkg";
                } 
                part 'CDT System' : SystemComponent { 
                    attribute :>> isAbstract = false; 
                    attribute :>> isActor = false; 
                    attribute :>> isDataComponent = false; 
                    attribute :>> isHuman = false; 
                    allocation '3ba3d777-5fdf-47fc-9de0-e769258e12e8' : ComponentFunctionalAllocation
                        allocate function ::> 'CDT_System Project'::'CDT_System'::'System Analysis'::'System Functions'::'Root System Function'.'Provide access to sensing device mounting'
                        to component ::> 'CDT_System Project'::'CDT_System'::'System Analysis'::'Structure'::'CDT System';
                    perform 'CDT_System Project'::'CDT_System'::'System Analysis'::'System Functions'::'Root System Function'.'Provide access to sensing device mounting' ; 
                    allocation '0c9a351f-df80-4201-a6bb-e7470bec1848' : ComponentFunctionalAllocation
                        allocate function ::> 'CDT_System Project'::'CDT_System'::'System Analysis'::'System Functions'::'Root System Function'.'Receive Athlete '
                        to component ::> 'CDT_System Project'::'CDT_System'::'System Analysis'::'Structure'::'CDT System';
                    perform 'CDT_System Project'::'CDT_System'::'System Analysis'::'System Functions'::'Root System Function'.'Receive Athlete ' ; 
                    allocation '9cd83368-f251-4653-8298-a225a6436ea3' : ComponentFunctionalAllocation
                        allocate function ::> 'CDT_System Project'::'CDT_System'::'System Analysis'::'System Functions'::'Root System Function'.'Helmet Receives a Hit'
                        to component ::> 'CDT_System Project'::'CDT_System'::'System Analysis'::'Structure'::'CDT System';
                    perform 'CDT_System Project'::'CDT_System'::'System Analysis'::'System Functions'::'Root System Function'.'Helmet Receives a Hit' ; 
                    allocation '59a4085e-0f48-4f21-ba81-7d39efc5099f' : ComponentFunctionalAllocation
                        allocate function ::> 'CDT_System Project'::'CDT_System'::'System Analysis'::'System Functions'::'Root System Function'.'Data stored'
                        to component ::> 'CDT_System Project'::'CDT_System'::'System Analysis'::'Structure'::'CDT System';
                    perform 'CDT_System Project'::'CDT_System'::'System Analysis'::'System Functions'::'Root System Function'.'Data stored' ; 
                    allocation 'de0eef46-0533-4fc2-839a-a7a4fa646e8a' : ComponentFunctionalAllocation
                        allocate function ::> 'CDT_System Project'::'CDT_System'::'System Analysis'::'System Functions'::'Root System Function'.'Data is Retrieved'
                        to component ::> 'CDT_System Project'::'CDT_System'::'System Analysis'::'Structure'::'CDT System';
                    perform 'CDT_System Project'::'CDT_System'::'System Analysis'::'System Functions'::'Root System Function'.'Data is Retrieved' ; 
                    allocation 'ced5d4c7-fe55-4185-8c9c-9df711b77ea5' : ComponentFunctionalAllocation
                        allocate function ::> 'CDT_System Project'::'CDT_System'::'System Analysis'::'System Functions'::'Root System Function'.'Device records Hit'
                        to component ::> 'CDT_System Project'::'CDT_System'::'System Analysis'::'Structure'::'CDT System';
                    perform 'CDT_System Project'::'CDT_System'::'System Analysis'::'System Functions'::'Root System Function'.'Device records Hit' ; 
                    allocation '41e0c4af-38a8-43ff-971c-13b5d72bc200' : ComponentFunctionalAllocation
                        allocate function ::> 'CDT_System Project'::'CDT_System'::'System Analysis'::'System Functions'::'Root System Function'.'Device alerts possible Concussion'
                        to component ::> 'CDT_System Project'::'CDT_System'::'System Analysis'::'Structure'::'CDT System';
                    perform 'CDT_System Project'::'CDT_System'::'System Analysis'::'System Functions'::'Root System Function'.'Device alerts possible Concussion' ; 
                    allocation '4b0d4e6c-b6e9-45ea-8460-e71291527c7a' : ComponentFunctionalAllocation
                        allocate function ::> 'CDT_System Project'::'CDT_System'::'System Analysis'::'System Functions'::'Root System Function'.'Enable Monitoring'
                        to component ::> 'CDT_System Project'::'CDT_System'::'System Analysis'::'Structure'::'CDT System';
                    perform 'CDT_System Project'::'CDT_System'::'System Analysis'::'System Functions'::'Root System Function'.'Enable Monitoring' ; 
                    allocation 'e4435d96-ef09-4f55-9406-2fd4c5b9861c' : ComponentFunctionalAllocation
                        allocate function ::> 'CDT_System Project'::'CDT_System'::'System Analysis'::'System Functions'::'Root System Function'.'Generates Reports'
                        to component ::> 'CDT_System Project'::'CDT_System'::'System Analysis'::'Structure'::'CDT System';
                    perform 'CDT_System Project'::'CDT_System'::'System Analysis'::'System Functions'::'Root System Function'.'Generates Reports' ; 
                    allocation '23d4594f-b142-4474-a685-b0817e111dbc' : ComponentFunctionalAllocation
                        allocate function ::> 'CDT_System Project'::'CDT_System'::'System Analysis'::'System Functions'::'Root System Function'.'Enable Secure Collection'
                        to component ::> 'CDT_System Project'::'CDT_System'::'System Analysis'::'Structure'::'CDT System';
                    perform 'CDT_System Project'::'CDT_System'::'System Analysis'::'System Functions'::'Root System Function'.'Enable Secure Collection' ; 
                    allocation 'bc82b6c8-7cca-43e6-993a-f0296f33e73b' : ComponentFunctionalAllocation
                        allocate function ::> 'CDT_System Project'::'CDT_System'::'System Analysis'::'System Functions'::'Root System Function'.'Recieve ID'
                        to component ::> 'CDT_System Project'::'CDT_System'::'System Analysis'::'Structure'::'CDT System';
                    perform 'CDT_System Project'::'CDT_System'::'System Analysis'::'System Functions'::'Root System Function'.'Recieve ID' ; 
                    allocation '767b7bfe-92c7-4980-918f-26c8f71f6dbc' : ComponentFunctionalAllocation
                        allocate function ::> 'CDT_System Project'::'CDT_System'::'System Analysis'::'System Functions'::'Root System Function'.'Provide access to helmut mounting'
                        to component ::> 'CDT_System Project'::'CDT_System'::'System Analysis'::'Structure'::'CDT System';
                    perform 'CDT_System Project'::'CDT_System'::'System Analysis'::'System Functions'::'Root System Function'.'Provide access to helmut mounting' ; 
                    allocation 'e72ab5bc-13c4-44b7-bab5-6e48c7d835aa' : ComponentFunctionalAllocation
                        allocate function ::> 'CDT_System Project'::'CDT_System'::'System Analysis'::'System Functions'::'Root System Function'.'Store Profile'
                        to component ::> 'CDT_System Project'::'CDT_System'::'System Analysis'::'Structure'::'CDT System';
                    perform 'CDT_System Project'::'CDT_System'::'System Analysis'::'System Functions'::'Root System Function'.'Store Profile' ; 
                    allocation 'f5f3e0a5-017c-44e8-92bd-8b3c315547ea' : ComponentFunctionalAllocation
                        allocate function ::> 'CDT_System Project'::'CDT_System'::'System Analysis'::'System Functions'::'Root System Function'.'Create Unique IDs for Athlete'
                        to component ::> 'CDT_System Project'::'CDT_System'::'System Analysis'::'Structure'::'CDT System';
                    perform 'CDT_System Project'::'CDT_System'::'System Analysis'::'System Functions'::'Root System Function'.'Create Unique IDs for Athlete' ; 
                    allocation '757eb69b-43d7-4fcc-98f8-bf172a88c725' : ComponentFunctionalAllocation
                        allocate function ::> 'CDT_System Project'::'CDT_System'::'System Analysis'::'System Functions'::'Root System Function'.'Provide ID Information'
                        to component ::> 'CDT_System Project'::'CDT_System'::'System Analysis'::'Structure'::'CDT System';
                    perform 'CDT_System Project'::'CDT_System'::'System Analysis'::'System Functions'::'Root System Function'.'Provide ID Information' ; 
                    allocation '92f02e02-f4e4-4136-bf98-da9e1150fc31' : ComponentFunctionalAllocation
                        allocate function ::> 'CDT_System Project'::'CDT_System'::'System Analysis'::'System Functions'::'Root System Function'.'Device'
                        to component ::> 'CDT_System Project'::'CDT_System'::'System Analysis'::'Structure'::'CDT System';
                    perform 'CDT_System Project'::'CDT_System'::'System Analysis'::'System Functions'::'Root System Function'.'Device' ; 
                    port 'CP 1' : ComponentPort { 
                        attribute :>> isDerived = false; 
                        attribute :>> aggregationKind = AggregationKind::UNSET; 
                        attribute :>> isFinal = false; 
                        attribute :>> kind = ComponentPortKind::STANDARD; 
                        attribute :>> isPartOfKey = false; 
                        attribute :>> isMaxInclusive = false; 
                        attribute :>> orientation = OrientationPortKind::UNSET; 
                        attribute :>> isUnique = false; 
                        attribute :>> isReadOnly = false; 
                        attribute :>> isMinInclusive = false; 
                        attribute :>> isStatic = false; 
                        attribute :>> isOrdered = false; 
                        attribute :>> isAbstract = false; 
                        ref allocation '4edb100c-6602-4366-bb00-ea9a900eaa41' : PortAllocation
                            allocate allocatedPort ::> 'CDT_System Project'::'CDT_System'::'System Analysis'::'System Functions'::'Root System Function'.'Helmet Receives a Hit'.'inActivity'
                            to allocatingPort ::> 'CDT_System Project'::'CDT_System'::'System Analysis'::'Structure'::'CDT System'.'CP 1'; 
                        ref :>> providedInterfaces =  ('CDT_System Project'::'CDT_System'::'System Analysis'::'Interfaces'::'Hit'); 
                        ref :>> ownedPortAllocations =  ('CDT_System Project'::'CDT_System'::'System Analysis'::'Structure'::'CDT System'.'CP 1'.'4edb100c-6602-4366-bb00-ea9a900eaa41'); 
                    }  
                    port 'CP 2' : ComponentPort { 
                        attribute :>> isDerived = false; 
                        attribute :>> aggregationKind = AggregationKind::UNSET; 
                        attribute :>> isFinal = false; 
                        attribute :>> kind = ComponentPortKind::STANDARD; 
                        attribute :>> isPartOfKey = false; 
                        attribute :>> isMaxInclusive = false; 
                        attribute :>> orientation = OrientationPortKind::UNSET; 
                        attribute :>> isUnique = false; 
                        attribute :>> isReadOnly = false; 
                        attribute :>> isMinInclusive = false; 
                        attribute :>> isStatic = false; 
                        attribute :>> isOrdered = false; 
                        attribute :>> isAbstract = false; 
                        ref allocation 'b80c80ae-b820-49a2-a4e3-010d8549ad87' : PortAllocation
                            allocate allocatedPort ::> 'CDT_System Project'::'CDT_System'::'System Analysis'::'System Functions'::'Root System Function'.'Device alerts possible Concussion'.'outConcussion Alert to Trainer'
                            to allocatingPort ::> 'CDT_System Project'::'CDT_System'::'System Analysis'::'Structure'::'CDT System'.'CP 2'; 
                        ref :>> ownedPortAllocations =  ('CDT_System Project'::'CDT_System'::'System Analysis'::'Structure'::'CDT System'.'CP 2'.'b80c80ae-b820-49a2-a4e3-010d8549ad87'); 
                        ref :>> requiredInterfaces =  ('CDT_System Project'::'CDT_System'::'System Analysis'::'Interfaces'::'Alert'); 
                    }  
                    state 'System State Machine' : StateMachine  { 
                        attribute :>> isControlOperator = false; 
                    }  
                    ref :>> ownedFunctionalAllocation =  ('CDT_System Project'::'CDT_System'::'System Analysis'::'Structure'::'CDT System'.'3ba3d777-5fdf-47fc-9de0-e769258e12e8',
                    'CDT_System Project'::'CDT_System'::'System Analysis'::'Structure'::'CDT System'.'0c9a351f-df80-4201-a6bb-e7470bec1848',
                    'CDT_System Project'::'CDT_System'::'System Analysis'::'Structure'::'CDT System'.'9cd83368-f251-4653-8298-a225a6436ea3',
                    'CDT_System Project'::'CDT_System'::'System Analysis'::'Structure'::'CDT System'.'59a4085e-0f48-4f21-ba81-7d39efc5099f',
                    'CDT_System Project'::'CDT_System'::'System Analysis'::'Structure'::'CDT System'.'de0eef46-0533-4fc2-839a-a7a4fa646e8a',
                    'CDT_System Project'::'CDT_System'::'System Analysis'::'Structure'::'CDT System'.'ced5d4c7-fe55-4185-8c9c-9df711b77ea5',
                    'CDT_System Project'::'CDT_System'::'System Analysis'::'Structure'::'CDT System'.'41e0c4af-38a8-43ff-971c-13b5d72bc200',
                    'CDT_System Project'::'CDT_System'::'System Analysis'::'Structure'::'CDT System'.'4b0d4e6c-b6e9-45ea-8460-e71291527c7a',
                    'CDT_System Project'::'CDT_System'::'System Analysis'::'Structure'::'CDT System'.'e4435d96-ef09-4f55-9406-2fd4c5b9861c',
                    'CDT_System Project'::'CDT_System'::'System Analysis'::'Structure'::'CDT System'.'23d4594f-b142-4474-a685-b0817e111dbc',
                    'CDT_System Project'::'CDT_System'::'System Analysis'::'Structure'::'CDT System'.'bc82b6c8-7cca-43e6-993a-f0296f33e73b',
                    'CDT_System Project'::'CDT_System'::'System Analysis'::'Structure'::'CDT System'.'767b7bfe-92c7-4980-918f-26c8f71f6dbc',
                    'CDT_System Project'::'CDT_System'::'System Analysis'::'Structure'::'CDT System'.'e72ab5bc-13c4-44b7-bab5-6e48c7d835aa',
                    'CDT_System Project'::'CDT_System'::'System Analysis'::'Structure'::'CDT System'.'f5f3e0a5-017c-44e8-92bd-8b3c315547ea',
                    'CDT_System Project'::'CDT_System'::'System Analysis'::'Structure'::'CDT System'.'757eb69b-43d7-4fcc-98f8-bf172a88c725',
                    'CDT_System Project'::'CDT_System'::'System Analysis'::'Structure'::'CDT System'.'92f02e02-f4e4-4136-bf98-da9e1150fc31'); 
                     
                     
                    ref :>> ownedStateMachines =  ('CDT_System Project'::'CDT_System'::'System Analysis'::'Structure'::'CDT System'.'System State Machine'); 
                }  
                part 'Trainer' : SystemComponent { 
                    attribute :>> isAbstract = false; 
                    attribute :>> isActor = true; 
                    attribute :>> isDataComponent = false; 
                    attribute :>> isHuman = false; 
                    allocation 'b07d19bb-3d4f-4fae-b993-2692d294e5e1' : ComponentFunctionalAllocation
                        allocate function ::> 'CDT_System Project'::'CDT_System'::'System Analysis'::'System Functions'::'Root System Function'.'Create profiles for Athletes'
                        to component ::> 'CDT_System Project'::'CDT_System'::'System Analysis'::'Structure'::'Trainer';
                    perform 'CDT_System Project'::'CDT_System'::'System Analysis'::'System Functions'::'Root System Function'.'Create profiles for Athletes' ; 
                    allocation '8cfe72fb-d28f-46c5-bf85-20379f7b372a' : ComponentFunctionalAllocation
                        allocate function ::> 'CDT_System Project'::'CDT_System'::'System Analysis'::'System Functions'::'Root System Function'.'Create Unique IDs'
                        to component ::> 'CDT_System Project'::'CDT_System'::'System Analysis'::'Structure'::'Trainer';
                    perform 'CDT_System Project'::'CDT_System'::'System Analysis'::'System Functions'::'Root System Function'.'Create Unique IDs' ; 
                    allocation 'bceeb626-cf3d-45d7-817c-a5230ebac612' : ComponentFunctionalAllocation
                        allocate function ::> 'CDT_System Project'::'CDT_System'::'System Analysis'::'System Functions'::'Root System Function'.'Provide ID to Athlete'
                        to component ::> 'CDT_System Project'::'CDT_System'::'System Analysis'::'Structure'::'Trainer';
                    perform 'CDT_System Project'::'CDT_System'::'System Analysis'::'System Functions'::'Root System Function'.'Provide ID to Athlete' ; 
                    allocation 'cefa2446-3c31-429f-9206-de06055bdb0c' : ComponentFunctionalAllocation
                        allocate function ::> 'CDT_System Project'::'CDT_System'::'System Analysis'::'System Functions'::'Root System Function'.'Assemble System Components'
                        to component ::> 'CDT_System Project'::'CDT_System'::'System Analysis'::'Structure'::'Trainer';
                    perform 'CDT_System Project'::'CDT_System'::'System Analysis'::'System Functions'::'Root System Function'.'Assemble System Components' ; 
                    allocation 'd0422ae9-1bb7-4aa1-8769-0fe5a153e4be' : ComponentFunctionalAllocation
                        allocate function ::> 'CDT_System Project'::'CDT_System'::'System Analysis'::'System Functions'::'Root System Function'.'Prep the device for use'
                        to component ::> 'CDT_System Project'::'CDT_System'::'System Analysis'::'Structure'::'Trainer';
                    perform 'CDT_System Project'::'CDT_System'::'System Analysis'::'System Functions'::'Root System Function'.'Prep the device for use' ; 
                    allocation 'da750b86-d339-4557-b04a-f003409494c4' : ComponentFunctionalAllocation
                        allocate function ::> 'CDT_System Project'::'CDT_System'::'System Analysis'::'System Functions'::'Root System Function'.'Recieve Enabled Signal from Athelete Helmet'
                        to component ::> 'CDT_System Project'::'CDT_System'::'System Analysis'::'Structure'::'Trainer';
                    perform 'CDT_System Project'::'CDT_System'::'System Analysis'::'System Functions'::'Root System Function'.'Recieve Enabled Signal from Athelete Helmet' ; 
                    allocation 'c762d8b3-af96-447b-a5d8-fba81f82b5f3' : ComponentFunctionalAllocation
                        allocate function ::> 'CDT_System Project'::'CDT_System'::'System Analysis'::'System Functions'::'Root System Function'.'Trainer Recieves Concussion Alert'
                        to component ::> 'CDT_System Project'::'CDT_System'::'System Analysis'::'Structure'::'Trainer';
                    perform 'CDT_System Project'::'CDT_System'::'System Analysis'::'System Functions'::'Root System Function'.'Trainer Recieves Concussion Alert' ; 
                    allocation 'f6bfe801-4382-418d-977c-a6d354cfcba9' : ComponentFunctionalAllocation
                        allocate function ::> 'CDT_System Project'::'CDT_System'::'System Analysis'::'System Functions'::'Root System Function'.'Data can be reviewed'
                        to component ::> 'CDT_System Project'::'CDT_System'::'System Analysis'::'Structure'::'Trainer';
                    perform 'CDT_System Project'::'CDT_System'::'System Analysis'::'System Functions'::'Root System Function'.'Data can be reviewed' ; 
                    allocation 'ffd90556-70f1-46d9-b695-261cef1838fd' : ComponentFunctionalAllocation
                        allocate function ::> 'CDT_System Project'::'CDT_System'::'System Analysis'::'System Functions'::'Root System Function'.'Executes Policies'
                        to component ::> 'CDT_System Project'::'CDT_System'::'System Analysis'::'Structure'::'Trainer';
                    perform 'CDT_System Project'::'CDT_System'::'System Analysis'::'System Functions'::'Root System Function'.'Executes Policies' ; 
                    port 'CP 1' : ComponentPort { 
                        attribute :>> isDerived = false; 
                        attribute :>> aggregationKind = AggregationKind::UNSET; 
                        attribute :>> isFinal = false; 
                        attribute :>> kind = ComponentPortKind::STANDARD; 
                        attribute :>> isPartOfKey = false; 
                        attribute :>> isMaxInclusive = false; 
                        attribute :>> orientation = OrientationPortKind::UNSET; 
                        attribute :>> isUnique = false; 
                        attribute :>> isReadOnly = false; 
                        attribute :>> isMinInclusive = false; 
                        attribute :>> isStatic = false; 
                        attribute :>> isOrdered = false; 
                        attribute :>> isAbstract = false; 
                        ref allocation '29d6517f-5bc6-4084-9e76-877aacccdd9c' : PortAllocation
                            allocate allocatedPort ::> 'CDT_System Project'::'CDT_System'::'System Analysis'::'System Functions'::'Root System Function'.'Trainer Recieves Concussion Alert'.'inConcussion Alert to Trainer'
                            to allocatingPort ::> 'CDT_System Project'::'CDT_System'::'System Analysis'::'Structure'::'Trainer'.'CP 1'; 
                        ref :>> providedInterfaces =  ('CDT_System Project'::'CDT_System'::'System Analysis'::'Interfaces'::'Alert'); 
                        ref :>> ownedPortAllocations =  ('CDT_System Project'::'CDT_System'::'System Analysis'::'Structure'::'Trainer'.'CP 1'.'29d6517f-5bc6-4084-9e76-877aacccdd9c'); 
                    }  
                    ref :>> ownedFunctionalAllocation =  ('CDT_System Project'::'CDT_System'::'System Analysis'::'Structure'::'Trainer'.'b07d19bb-3d4f-4fae-b993-2692d294e5e1',
                    'CDT_System Project'::'CDT_System'::'System Analysis'::'Structure'::'Trainer'.'8cfe72fb-d28f-46c5-bf85-20379f7b372a',
                    'CDT_System Project'::'CDT_System'::'System Analysis'::'Structure'::'Trainer'.'bceeb626-cf3d-45d7-817c-a5230ebac612',
                    'CDT_System Project'::'CDT_System'::'System Analysis'::'Structure'::'Trainer'.'cefa2446-3c31-429f-9206-de06055bdb0c',
                    'CDT_System Project'::'CDT_System'::'System Analysis'::'Structure'::'Trainer'.'d0422ae9-1bb7-4aa1-8769-0fe5a153e4be',
                    'CDT_System Project'::'CDT_System'::'System Analysis'::'Structure'::'Trainer'.'da750b86-d339-4557-b04a-f003409494c4',
                    'CDT_System Project'::'CDT_System'::'System Analysis'::'Structure'::'Trainer'.'c762d8b3-af96-447b-a5d8-fba81f82b5f3',
                    'CDT_System Project'::'CDT_System'::'System Analysis'::'Structure'::'Trainer'.'f6bfe801-4382-418d-977c-a6d354cfcba9',
                    'CDT_System Project'::'CDT_System'::'System Analysis'::'Structure'::'Trainer'.'ffd90556-70f1-46d9-b695-261cef1838fd'); 
                     
                     
                }  
                part 'Parent' : SystemComponent { 
                    attribute :>> isAbstract = false; 
                    attribute :>> isActor = true; 
                    attribute :>> isDataComponent = false; 
                    attribute :>> isHuman = false; 
                    allocation 'e0b9eb64-003e-4f9f-8f96-1c0e8aa9893e' : ComponentFunctionalAllocation
                        allocate function ::> 'CDT_System Project'::'CDT_System'::'System Analysis'::'System Functions'::'Root System Function'.'Report received'
                        to component ::> 'CDT_System Project'::'CDT_System'::'System Analysis'::'Structure'::'Parent';
                    perform 'CDT_System Project'::'CDT_System'::'System Analysis'::'System Functions'::'Root System Function'.'Report received' ; 
                    ref :>> ownedFunctionalAllocation =  ('CDT_System Project'::'CDT_System'::'System Analysis'::'Structure'::'Parent'.'e0b9eb64-003e-4f9f-8f96-1c0e8aa9893e'); 
                     
                     
                }  
                part 'Athlete' : SystemComponent { 
                    attribute :>> isAbstract = false; 
                    attribute :>> isActor = true; 
                    attribute :>> isDataComponent = false; 
                    attribute :>> isHuman = false; 
                    allocation 'a18e9219-37c4-43cd-92a7-a2c87cd38082' : ComponentFunctionalAllocation
                        allocate function ::> 'CDT_System Project'::'CDT_System'::'System Analysis'::'System Functions'::'Root System Function'.'Provide Data for Profile'
                        to component ::> 'CDT_System Project'::'CDT_System'::'System Analysis'::'Structure'::'Athlete';
                    perform 'CDT_System Project'::'CDT_System'::'System Analysis'::'System Functions'::'Root System Function'.'Provide Data for Profile' ; 
                    allocation 'ff7fa76c-16d9-413a-b2ad-0b306e5c4ed9' : ComponentFunctionalAllocation
                        allocate function ::> 'CDT_System Project'::'CDT_System'::'System Analysis'::'System Functions'::'Root System Function'.'Recieve ID'
                        to component ::> 'CDT_System Project'::'CDT_System'::'System Analysis'::'Structure'::'Athlete';
                    perform 'CDT_System Project'::'CDT_System'::'System Analysis'::'System Functions'::'Root System Function'.'Recieve ID' ; 
                    allocation '2292ea57-cdf1-46e1-bfaa-5509c9c123c0' : ComponentFunctionalAllocation
                        allocate function ::> 'CDT_System Project'::'CDT_System'::'System Analysis'::'System Functions'::'Root System Function'.'Insert ID into Sensing Device'
                        to component ::> 'CDT_System Project'::'CDT_System'::'System Analysis'::'Structure'::'Athlete';
                    perform 'CDT_System Project'::'CDT_System'::'System Analysis'::'System Functions'::'Root System Function'.'Insert ID into Sensing Device' ; 
                    allocation 'a0c565fe-d3b3-4114-9e37-95cf8f614c1e' : ComponentFunctionalAllocation
                        allocate function ::> 'CDT_System Project'::'CDT_System'::'System Analysis'::'System Functions'::'Root System Function'.'Place on Helmet'
                        to component ::> 'CDT_System Project'::'CDT_System'::'System Analysis'::'Structure'::'Athlete';
                    perform 'CDT_System Project'::'CDT_System'::'System Analysis'::'System Functions'::'Root System Function'.'Place on Helmet' ; 
                    allocation '827d3f34-1fce-4302-82e8-ad1f79367fdf' : ComponentFunctionalAllocation
                        allocate function ::> 'CDT_System Project'::'CDT_System'::'System Analysis'::'System Functions'::'Root System Function'.'Athlete Particpates in Activity'
                        to component ::> 'CDT_System Project'::'CDT_System'::'System Analysis'::'Structure'::'Athlete';
                    perform 'CDT_System Project'::'CDT_System'::'System Analysis'::'System Functions'::'Root System Function'.'Athlete Particpates in Activity' ; 
                    allocation '537e7b9e-3852-4fe9-94b1-102718a23ea3' : ComponentFunctionalAllocation
                        allocate function ::> 'CDT_System Project'::'CDT_System'::'System Analysis'::'System Functions'::'Root System Function'.'Yield to Evaluation'
                        to component ::> 'CDT_System Project'::'CDT_System'::'System Analysis'::'Structure'::'Athlete';
                    perform 'CDT_System Project'::'CDT_System'::'System Analysis'::'System Functions'::'Root System Function'.'Yield to Evaluation' ; 
                    allocation 'aa205db6-bd7e-4ee1-8105-4aaa9f9601c8' : ComponentFunctionalAllocation
                        allocate function ::> 'CDT_System Project'::'CDT_System'::'System Analysis'::'System Functions'::'Root System Function'.'Report Received'
                        to component ::> 'CDT_System Project'::'CDT_System'::'System Analysis'::'Structure'::'Athlete';
                    perform 'CDT_System Project'::'CDT_System'::'System Analysis'::'System Functions'::'Root System Function'.'Report Received' ; 
                    port 'CP 1' : ComponentPort { 
                        attribute :>> isDerived = false; 
                        attribute :>> aggregationKind = AggregationKind::UNSET; 
                        attribute :>> isFinal = false; 
                        attribute :>> kind = ComponentPortKind::STANDARD; 
                        attribute :>> isPartOfKey = false; 
                        attribute :>> isMaxInclusive = false; 
                        attribute :>> orientation = OrientationPortKind::UNSET; 
                        attribute :>> isUnique = false; 
                        attribute :>> isReadOnly = false; 
                        attribute :>> isMinInclusive = false; 
                        attribute :>> isStatic = false; 
                        attribute :>> isOrdered = false; 
                        attribute :>> isAbstract = false; 
                        ref allocation '57c7bd0f-f9ef-4e4e-ba13-700fa295fc38' : PortAllocation
                            allocate allocatedPort ::> 'CDT_System Project'::'CDT_System'::'System Analysis'::'System Functions'::'Root System Function'.'Athlete Particpates in Activity'.'outActivity'
                            to allocatingPort ::> 'CDT_System Project'::'CDT_System'::'System Analysis'::'Structure'::'Athlete'.'CP 1'; 
                        ref :>> ownedPortAllocations =  ('CDT_System Project'::'CDT_System'::'System Analysis'::'Structure'::'Athlete'.'CP 1'.'57c7bd0f-f9ef-4e4e-ba13-700fa295fc38'); 
                        ref :>> requiredInterfaces =  ('CDT_System Project'::'CDT_System'::'System Analysis'::'Interfaces'::'Hit'); 
                    }  
                    ref :>> ownedFunctionalAllocation =  ('CDT_System Project'::'CDT_System'::'System Analysis'::'Structure'::'Athlete'.'a18e9219-37c4-43cd-92a7-a2c87cd38082',
                    'CDT_System Project'::'CDT_System'::'System Analysis'::'Structure'::'Athlete'.'ff7fa76c-16d9-413a-b2ad-0b306e5c4ed9',
                    'CDT_System Project'::'CDT_System'::'System Analysis'::'Structure'::'Athlete'.'2292ea57-cdf1-46e1-bfaa-5509c9c123c0',
                    'CDT_System Project'::'CDT_System'::'System Analysis'::'Structure'::'Athlete'.'a0c565fe-d3b3-4114-9e37-95cf8f614c1e',
                    'CDT_System Project'::'CDT_System'::'System Analysis'::'Structure'::'Athlete'.'827d3f34-1fce-4302-82e8-ad1f79367fdf',
                    'CDT_System Project'::'CDT_System'::'System Analysis'::'Structure'::'Athlete'.'537e7b9e-3852-4fe9-94b1-102718a23ea3',
                    'CDT_System Project'::'CDT_System'::'System Analysis'::'Structure'::'Athlete'.'aa205db6-bd7e-4ee1-8105-4aaa9f9601c8'); 
                     
                     
                }  
                part 'Instituion' : SystemComponent { 
                    attribute :>> isAbstract = false; 
                    attribute :>> isActor = true; 
                    attribute :>> isDataComponent = false; 
                    attribute :>> isHuman = false; 
                    allocation '9928d191-a435-446d-8393-c8714079af3b' : ComponentFunctionalAllocation
                        allocate function ::> 'CDT_System Project'::'CDT_System'::'System Analysis'::'System Functions'::'Root System Function'.'Aquire System'
                        to component ::> 'CDT_System Project'::'CDT_System'::'System Analysis'::'Structure'::'Instituion';
                    perform 'CDT_System Project'::'CDT_System'::'System Analysis'::'System Functions'::'Root System Function'.'Aquire System' ; 
                    allocation '4f3d203a-74be-4f3e-b444-17c2b5443576' : ComponentFunctionalAllocation
                        allocate function ::> 'CDT_System Project'::'CDT_System'::'System Analysis'::'System Functions'::'Root System Function'.'Report Received'
                        to component ::> 'CDT_System Project'::'CDT_System'::'System Analysis'::'Structure'::'Instituion';
                    perform 'CDT_System Project'::'CDT_System'::'System Analysis'::'System Functions'::'Root System Function'.'Report Received' ; 
                    allocation '47f52431-d2e1-4273-aa23-0e9e2aa242ec' : ComponentFunctionalAllocation
                        allocate function ::> 'CDT_System Project'::'CDT_System'::'System Analysis'::'System Functions'::'Root System Function'.'Established Concussion Policy'
                        to component ::> 'CDT_System Project'::'CDT_System'::'System Analysis'::'Structure'::'Instituion';
                    perform 'CDT_System Project'::'CDT_System'::'System Analysis'::'System Functions'::'Root System Function'.'Established Concussion Policy' ; 
                    ref :>> ownedFunctionalAllocation =  ('CDT_System Project'::'CDT_System'::'System Analysis'::'Structure'::'Instituion'.'9928d191-a435-446d-8393-c8714079af3b',
                    'CDT_System Project'::'CDT_System'::'System Analysis'::'Structure'::'Instituion'.'4f3d203a-74be-4f3e-b444-17c2b5443576',
                    'CDT_System Project'::'CDT_System'::'System Analysis'::'Structure'::'Instituion'.'47f52431-d2e1-4273-aa23-0e9e2aa242ec'); 
                     
                     
                }  
                part 'Secure Cloud' : SystemComponent { 
                    attribute :>> isAbstract = false; 
                    attribute :>> isActor = false; 
                    attribute :>> isDataComponent = false; 
                    attribute :>> isHuman = false; 
                     
                }  
                part 'ID Device' : SystemComponent { 
                    attribute :>> isAbstract = false; 
                    attribute :>> isActor = false; 
                    attribute :>> isDataComponent = false; 
                    attribute :>> isHuman = false; 
                     
                }  
                part 'Helmet' : SystemComponent { 
                    attribute :>> isAbstract = false; 
                    attribute :>> isActor = false; 
                    attribute :>> isDataComponent = false; 
                    attribute :>> isHuman = false; 
                     
                }  
                part 'Sensing Device' : SystemComponent { 
                    attribute :>> isAbstract = false; 
                    attribute :>> isActor = false; 
                    attribute :>> isDataComponent = false; 
                    attribute :>> isHuman = false; 
                     
                }  
                interface '58923afe-a210-4ecc-96e2-34de8f1563b7' : ComponentExchange 
                    connect source ::> 'CDT_System Project'::'CDT_System'::'System Analysis'::'Structure'::'Athlete'.'CP 1'
                    to  target ::> 'CDT_System Project'::'CDT_System'::'System Analysis'::'Structure'::'CDT System'.'CP 1' { 
                    attribute :>> isOriented = false; 
                    attribute :>> interfaceName = "Hit"; 
                    attribute :>> kind = ComponentExchangeKind::ASSEMBLY; 
                    allocation '9ebfa562-c3c9-4996-a949-0a6d6b7a0c76' : ComponentExchangeFunctionalExchangeAllocation
                        allocate functionalExchange ::> 'CDT_System Project'::'CDT_System'::'System Analysis'::'System Functions'::'Root System Function'.'97a72935-6d79-46ff-b4b7-1d130ca15b47'
                        to componentExchange ::> 'CDT_System Project'::'CDT_System'::'System Analysis'::'Structure'::'58923afe-a210-4ecc-96e2-34de8f1563b7'; 
                    ref :>> ownedComponentExchangeFunctionalExchangeAllocations =  ('CDT_System Project'::'CDT_System'::'System Analysis'::'Structure'::'58923afe-a210-4ecc-96e2-34de8f1563b7'.'9ebfa562-c3c9-4996-a949-0a6d6b7a0c76'); 
                }  
                interface 'e37fb774-5ee6-43f6-844a-cced53c9ed20' : ComponentExchange 
                    connect source ::> 'CDT_System Project'::'CDT_System'::'System Analysis'::'Structure'::'CDT System'.'CP 2'
                    to  target ::> 'CDT_System Project'::'CDT_System'::'System Analysis'::'Structure'::'Trainer'.'CP 1' { 
                    attribute :>> isOriented = false; 
                    attribute :>> interfaceName = "Alert"; 
                    attribute :>> kind = ComponentExchangeKind::ASSEMBLY; 
                    allocation 'd988ff62-c8dc-4331-bf52-44ab626d2612' : ComponentExchangeFunctionalExchangeAllocation
                        allocate functionalExchange ::> 'CDT_System Project'::'CDT_System'::'System Analysis'::'System Functions'::'Root System Function'.'8520e06a-fe44-4659-8276-5a2d135f9211'
                        to componentExchange ::> 'CDT_System Project'::'CDT_System'::'System Analysis'::'Structure'::'e37fb774-5ee6-43f6-844a-cced53c9ed20'; 
                    ref :>> ownedComponentExchangeFunctionalExchangeAllocations =  ('CDT_System Project'::'CDT_System'::'System Analysis'::'Structure'::'e37fb774-5ee6-43f6-844a-cced53c9ed20'.'d988ff62-c8dc-4331-bf52-44ab626d2612'); 
                }  
            } 
        } 
        package  'Logical Architecture' {
            @PackageMeta {
                type = "LogicalArchitecture";
            } 
            package  'Data' {
                @PackageMeta {
                    type = "DataPkg";
                } 
            } 
            package  'Structure' {
                @PackageMeta {
                    type = "LogicalComponentPkg";
                } 
                part 'CDT System' : LogicalComponent { 
                    attribute :>> isAbstract = false; 
                    attribute :>> isActor = false; 
                    attribute :>> isHuman = false; 
                    part 'Secure Application' : LogicalComponent { 
                        attribute :>> isAbstract = false; 
                        attribute :>> isActor = false; 
                        attribute :>> isHuman = false; 
                        allocation '5bfa5054-c93e-4cc1-b8e1-598e0fdad810' : ComponentFunctionalAllocation
                            allocate function ::> 'CDT_System Project'::'CDT_System'::'Logical Architecture'::'Logical Functions'::'Root Logical Function'.'Device alerts possible Concussion'.'Record the Concussion'
                            to component ::> 'CDT_System Project'::'CDT_System'::'Logical Architecture'::'Structure'::'CDT System'.'Secure Application';
                        perform 'CDT_System Project'::'CDT_System'::'Logical Architecture'::'Logical Functions'::'Root Logical Function'.'Device alerts possible Concussion'.'Record the Concussion' ; 
                        allocation 'ba68a87f-7f12-4951-a540-ca19bdbaf6a6' : ComponentFunctionalAllocation
                            allocate function ::> 'CDT_System Project'::'CDT_System'::'Logical Architecture'::'Logical Functions'::'Root Logical Function'.'Data stored'.'Data Stored'
                            to component ::> 'CDT_System Project'::'CDT_System'::'Logical Architecture'::'Structure'::'CDT System'.'Secure Application';
                        perform 'CDT_System Project'::'CDT_System'::'Logical Architecture'::'Logical Functions'::'Root Logical Function'.'Data stored'.'Data Stored' ; 
                        allocation 'c97f75c3-5568-40b1-acb7-72f033af2839' : ComponentFunctionalAllocation
                            allocate function ::> 'CDT_System Project'::'CDT_System'::'Logical Architecture'::'Logical Functions'::'Root Logical Function'.'Generates Reports'.'Generate Reports'
                            to component ::> 'CDT_System Project'::'CDT_System'::'Logical Architecture'::'Structure'::'CDT System'.'Secure Application';
                        perform 'CDT_System Project'::'CDT_System'::'Logical Architecture'::'Logical Functions'::'Root Logical Function'.'Generates Reports'.'Generate Reports' ; 
                        allocation 'de255230-31ef-444a-ad44-113d63988e58' : ComponentFunctionalAllocation
                            allocate function ::> 'CDT_System Project'::'CDT_System'::'Logical Architecture'::'Logical Functions'::'Root Logical Function'.'Enable Monitoring'.'Enable Recored'
                            to component ::> 'CDT_System Project'::'CDT_System'::'Logical Architecture'::'Structure'::'CDT System'.'Secure Application';
                        perform 'CDT_System Project'::'CDT_System'::'Logical Architecture'::'Logical Functions'::'Root Logical Function'.'Enable Monitoring'.'Enable Recored' ; 
                        allocation '15431656-1b85-44f4-8edb-a44bbdc73678' : ComponentFunctionalAllocation
                            allocate function ::> 'CDT_System Project'::'CDT_System'::'Logical Architecture'::'Logical Functions'::'Root Logical Function'.'Store Profile'.'Store Profile'
                            to component ::> 'CDT_System Project'::'CDT_System'::'Logical Architecture'::'Structure'::'CDT System'.'Secure Application';
                        perform 'CDT_System Project'::'CDT_System'::'Logical Architecture'::'Logical Functions'::'Root Logical Function'.'Store Profile'.'Store Profile' ; 
                        allocation '469b6dfe-438b-4184-96b8-d213c969859e' : ComponentFunctionalAllocation
                            allocate function ::> 'CDT_System Project'::'CDT_System'::'Logical Architecture'::'Logical Functions'::'Root Logical Function'.'Create Unique IDs for Athlete'.'Create ID'
                            to component ::> 'CDT_System Project'::'CDT_System'::'Logical Architecture'::'Structure'::'CDT System'.'Secure Application';
                        perform 'CDT_System Project'::'CDT_System'::'Logical Architecture'::'Logical Functions'::'Root Logical Function'.'Create Unique IDs for Athlete'.'Create ID' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '9c2abf86-a0a1-49a1-9cfa-c9c58b1450ba' : PortAllocation
                                allocate allocatedPort ::> 'CDT_System Project'::'CDT_System'::'Logical Architecture'::'Logical Functions'::'Root Logical Function'.'Device alerts possible Concussion'.'Record the Concussion'.'FIP 1'
                                to allocatingPort ::> 'CDT_System Project'::'CDT_System'::'Logical Architecture'::'Structure'::'CDT System'.'Secure Application'.'CP 1'; 
                            ref allocation '7de53c98-dcd0-44a4-aed9-6cb0506025db' : PortAllocation
                                allocate allocatedPort ::> 'CDT_System Project'::'CDT_System'::'Logical Architecture'::'Logical Functions'::'Root Logical Function'.'Enable Monitoring'.'Enable Recored'.'FIP 1'
                                to allocatingPort ::> 'CDT_System Project'::'CDT_System'::'Logical Architecture'::'Structure'::'CDT System'.'Secure Application'.'CP 1'; 
                            ref :>> providedInterfaces =  ('CDT_System Project'::'CDT_System'::'Logical Architecture'::'Interfaces'::'Lora - SA'); 
                            ref :>> ownedPortAllocations =  ('CDT_System Project'::'CDT_System'::'Logical Architecture'::'Structure'::'CDT System'.'Secure Application'.'CP 1'.'9c2abf86-a0a1-49a1-9cfa-c9c58b1450ba',
                            'CDT_System Project'::'CDT_System'::'Logical Architecture'::'Structure'::'CDT System'.'Secure Application'.'CP 1'.'7de53c98-dcd0-44a4-aed9-6cb0506025db'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'daafb378-4c83-49d0-a20d-53c6b81af327' : PortAllocation
                                allocate allocatedPort ::> 'CDT_System Project'::'CDT_System'::'Logical Architecture'::'Logical Functions'::'Root Logical Function'.'Device alerts possible Concussion'.'Record the Concussion'.'FOP 2'
                                to allocatingPort ::> 'CDT_System Project'::'CDT_System'::'Logical Architecture'::'Structure'::'CDT System'.'Secure Application'.'CP 2'; 
                            ref allocation 'd43d9b6c-ecc1-44ec-97c9-025fcfb9d576' : PortAllocation
                                allocate allocatedPort ::> 'CDT_System Project'::'CDT_System'::'Logical Architecture'::'Logical Functions'::'Root Logical Function'.'Enable Monitoring'.'Enable Recored'.'FOP 1'
                                to allocatingPort ::> 'CDT_System Project'::'CDT_System'::'Logical Architecture'::'Structure'::'CDT System'.'Secure Application'.'CP 2'; 
                            ref allocation '4a6ac492-d52f-4150-b8cb-ad8f0f477d19' : PortAllocation
                                allocate allocatedPort ::> 'CDT_System Project'::'CDT_System'::'Logical Architecture'::'Logical Functions'::'Root Logical Function'.'Data stored'.'Data Stored'.'FOP 1'
                                to allocatingPort ::> 'CDT_System Project'::'CDT_System'::'Logical Architecture'::'Structure'::'CDT System'.'Secure Application'.'CP 2'; 
                            ref allocation 'e801103a-e119-4d14-8f5b-e32caed8fa4f' : PortAllocation
                                allocate allocatedPort ::> 'CDT_System Project'::'CDT_System'::'Logical Architecture'::'Logical Functions'::'Root Logical Function'.'Store Profile'.'Store Profile'.'FIP 1'
                                to allocatingPort ::> 'CDT_System Project'::'CDT_System'::'Logical Architecture'::'Structure'::'CDT System'.'Secure Application'.'CP 2'; 
                            ref allocation '133bf8db-61e6-443b-a773-875170177782' : PortAllocation
                                allocate allocatedPort ::> 'CDT_System Project'::'CDT_System'::'Logical Architecture'::'Logical Functions'::'Root Logical Function'.'Create Unique IDs for Athlete'.'Create ID'.'FIP 1'
                                to allocatingPort ::> 'CDT_System Project'::'CDT_System'::'Logical Architecture'::'Structure'::'CDT System'.'Secure Application'.'CP 2'; 
                            ref allocation '0d4e3ddf-373f-494a-ac55-4ecaef515774' : PortAllocation
                                allocate allocatedPort ::> 'CDT_System Project'::'CDT_System'::'Logical Architecture'::'Logical Functions'::'Root Logical Function'.'Data stored'.'Data Stored'.'inRecorded Data'
                                to allocatingPort ::> 'CDT_System Project'::'CDT_System'::'Logical Architecture'::'Structure'::'CDT System'.'Secure Application'.'CP 2'; 
                            ref allocation '5a54f7d9-9a99-4214-b5ea-25db6f22bf40' : PortAllocation
                                allocate allocatedPort ::> 'CDT_System Project'::'CDT_System'::'Logical Architecture'::'Logical Functions'::'Root Logical Function'.'Generates Reports'.'Generate Reports'.'FIP 1'
                                to allocatingPort ::> 'CDT_System Project'::'CDT_System'::'Logical Architecture'::'Structure'::'CDT System'.'Secure Application'.'CP 2'; 
                            ref :>> providedInterfaces =  ('CDT_System Project'::'CDT_System'::'Logical Architecture'::'Interfaces'::'SA-CDT App'); 
                            ref :>> ownedPortAllocations =  ('CDT_System Project'::'CDT_System'::'Logical Architecture'::'Structure'::'CDT System'.'Secure Application'.'CP 2'.'daafb378-4c83-49d0-a20d-53c6b81af327',
                            'CDT_System Project'::'CDT_System'::'Logical Architecture'::'Structure'::'CDT System'.'Secure Application'.'CP 2'.'d43d9b6c-ecc1-44ec-97c9-025fcfb9d576',
                            'CDT_System Project'::'CDT_System'::'Logical Architecture'::'Structure'::'CDT System'.'Secure Application'.'CP 2'.'4a6ac492-d52f-4150-b8cb-ad8f0f477d19',
                            'CDT_System Project'::'CDT_System'::'Logical Architecture'::'Structure'::'CDT System'.'Secure Application'.'CP 2'.'e801103a-e119-4d14-8f5b-e32caed8fa4f',
                            'CDT_System Project'::'CDT_System'::'Logical Architecture'::'Structure'::'CDT System'.'Secure Application'.'CP 2'.'133bf8db-61e6-443b-a773-875170177782',
                            'CDT_System Project'::'CDT_System'::'Logical Architecture'::'Structure'::'CDT System'.'Secure Application'.'CP 2'.'0d4e3ddf-373f-494a-ac55-4ecaef515774',
                            'CDT_System Project'::'CDT_System'::'Logical Architecture'::'Structure'::'CDT System'.'Secure Application'.'CP 2'.'5a54f7d9-9a99-4214-b5ea-25db6f22bf40'); 
                            ref :>> requiredInterfaces =  ('CDT_System Project'::'CDT_System'::'Logical Architecture'::'Interfaces'::'SA-CDT App'); 
                        }  
                        port 'CP 3' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '88ba3933-64ba-4180-9d64-e795826b46b3' : PortAllocation
                                allocate allocatedPort ::> 'CDT_System Project'::'CDT_System'::'Logical Architecture'::'Logical Functions'::'Root Logical Function'.'Generates Reports'.'Generate Reports'.'outAthlete Report'
                                to allocatingPort ::> 'CDT_System Project'::'CDT_System'::'Logical Architecture'::'Structure'::'CDT System'.'Secure Application'.'CP 3'; 
                            ref :>> ownedPortAllocations =  ('CDT_System Project'::'CDT_System'::'Logical Architecture'::'Structure'::'CDT System'.'Secure Application'.'CP 3'.'88ba3933-64ba-4180-9d64-e795826b46b3'); 
                            ref :>> requiredInterfaces =  ('CDT_System Project'::'CDT_System'::'Logical Architecture'::'Interfaces'::'SA- Athlete'); 
                        }  
                        port 'CP 4' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'a106132b-472a-4e8a-8987-3867461bac4c' : PortAllocation
                                allocate allocatedPort ::> 'CDT_System Project'::'CDT_System'::'Logical Architecture'::'Logical Functions'::'Root Logical Function'.'Generates Reports'.'Generate Reports'.'outInstition Report'
                                to allocatingPort ::> 'CDT_System Project'::'CDT_System'::'Logical Architecture'::'Structure'::'CDT System'.'Secure Application'.'CP 4'; 
                            ref :>> ownedPortAllocations =  ('CDT_System Project'::'CDT_System'::'Logical Architecture'::'Structure'::'CDT System'.'Secure Application'.'CP 4'.'a106132b-472a-4e8a-8987-3867461bac4c'); 
                            ref :>> requiredInterfaces =  ('CDT_System Project'::'CDT_System'::'Logical Architecture'::'Interfaces'::'SA-Inst'); 
                        }  
                        port 'CP 5' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'c7da91d8-a48d-4f6a-b343-62f8304c4a5a' : PortAllocation
                                allocate allocatedPort ::> 'CDT_System Project'::'CDT_System'::'Logical Architecture'::'Logical Functions'::'Root Logical Function'.'Generates Reports'.'Generate Reports'.'outParen Report'
                                to allocatingPort ::> 'CDT_System Project'::'CDT_System'::'Logical Architecture'::'Structure'::'CDT System'.'Secure Application'.'CP 5'; 
                            ref :>> ownedPortAllocations =  ('CDT_System Project'::'CDT_System'::'Logical Architecture'::'Structure'::'CDT System'.'Secure Application'.'CP 5'.'c7da91d8-a48d-4f6a-b343-62f8304c4a5a'); 
                            ref :>> requiredInterfaces =  ('CDT_System Project'::'CDT_System'::'Logical Architecture'::'Interfaces'::'SA-Parent'); 
                        }  
                        ref :>> ownedFunctionalAllocation =  ('CDT_System Project'::'CDT_System'::'Logical Architecture'::'Structure'::'CDT System'.'Secure Application'.'5bfa5054-c93e-4cc1-b8e1-598e0fdad810',
                        'CDT_System Project'::'CDT_System'::'Logical Architecture'::'Structure'::'CDT System'.'Secure Application'.'ba68a87f-7f12-4951-a540-ca19bdbaf6a6',
                        'CDT_System Project'::'CDT_System'::'Logical Architecture'::'Structure'::'CDT System'.'Secure Application'.'c97f75c3-5568-40b1-acb7-72f033af2839',
                        'CDT_System Project'::'CDT_System'::'Logical Architecture'::'Structure'::'CDT System'.'Secure Application'.'de255230-31ef-444a-ad44-113d63988e58',
                        'CDT_System Project'::'CDT_System'::'Logical Architecture'::'Structure'::'CDT System'.'Secure Application'.'15431656-1b85-44f4-8edb-a44bbdc73678',
                        'CDT_System Project'::'CDT_System'::'Logical Architecture'::'Structure'::'CDT System'.'Secure Application'.'469b6dfe-438b-4184-96b8-d213c969859e'); 
                    }  
                    part 'ID Device' : LogicalComponent { 
                        attribute :>> isAbstract = false; 
                        attribute :>> isActor = false; 
                        attribute :>> isHuman = false; 
                        allocation 'd5f99d4d-a19f-45ab-8efd-5015e2096676' : ComponentFunctionalAllocation
                            allocate function ::> 'CDT_System Project'::'CDT_System'::'Logical Architecture'::'Logical Functions'::'Root Logical Function'.'Provide ID Information'
                            to component ::> 'CDT_System Project'::'CDT_System'::'Logical Architecture'::'Structure'::'CDT System'.'ID Device';
                        perform 'CDT_System Project'::'CDT_System'::'Logical Architecture'::'Logical Functions'::'Root Logical Function'.'Provide ID Information' ; 
                        allocation 'c398e0ec-c416-4242-9438-b901e9353e4c' : ComponentFunctionalAllocation
                            allocate function ::> 'CDT_System Project'::'CDT_System'::'Logical Architecture'::'Logical Functions'::'Root Logical Function'.'Create Unique IDs for Athlete'.'Create and Program ID'
                            to component ::> 'CDT_System Project'::'CDT_System'::'Logical Architecture'::'Structure'::'CDT System'.'ID Device';
                        perform 'CDT_System Project'::'CDT_System'::'Logical Architecture'::'Logical Functions'::'Root Logical Function'.'Create Unique IDs for Athlete'.'Create and Program ID' ; 
                        ref :>> ownedFunctionalAllocation =  ('CDT_System Project'::'CDT_System'::'Logical Architecture'::'Structure'::'CDT System'.'ID Device'.'d5f99d4d-a19f-45ab-8efd-5015e2096676',
                        'CDT_System Project'::'CDT_System'::'Logical Architecture'::'Structure'::'CDT System'.'ID Device'.'c398e0ec-c416-4242-9438-b901e9353e4c'); 
                    }  
                    part 'Helmet Receives a Hit' : LogicalComponent { 
                        attribute :>> isAbstract = false; 
                        attribute :>> isActor = false; 
                        attribute :>> isHuman = false; 
                        allocation 'eebdb447-be21-49c1-9bd6-2843c0c1300b' : ComponentFunctionalAllocation
                            allocate function ::> 'CDT_System Project'::'CDT_System'::'Logical Architecture'::'Logical Functions'::'Root Logical Function'.'Provide access to sensing device mounting'
                            to component ::> 'CDT_System Project'::'CDT_System'::'Logical Architecture'::'Structure'::'CDT System'.'Helmet Receives a Hit';
                        perform 'CDT_System Project'::'CDT_System'::'Logical Architecture'::'Logical Functions'::'Root Logical Function'.'Provide access to sensing device mounting' ; 
                        allocation 'a7381b8d-cba9-4b08-a0da-6e77187a3291' : ComponentFunctionalAllocation
                            allocate function ::> 'CDT_System Project'::'CDT_System'::'Logical Architecture'::'Logical Functions'::'Root Logical Function'.'Receive Athlete '
                            to component ::> 'CDT_System Project'::'CDT_System'::'Logical Architecture'::'Structure'::'CDT System'.'Helmet Receives a Hit';
                        perform 'CDT_System Project'::'CDT_System'::'Logical Architecture'::'Logical Functions'::'Root Logical Function'.'Receive Athlete ' ; 
                        allocation '5501b3fe-aee9-46de-8556-bb2704e5c054' : ComponentFunctionalAllocation
                            allocate function ::> 'CDT_System Project'::'CDT_System'::'Logical Architecture'::'Logical Functions'::'Root Logical Function'.'Helmet Receives a Hit'
                            to component ::> 'CDT_System Project'::'CDT_System'::'Logical Architecture'::'Structure'::'CDT System'.'Helmet Receives a Hit';
                        perform 'CDT_System Project'::'CDT_System'::'Logical Architecture'::'Logical Functions'::'Root Logical Function'.'Helmet Receives a Hit' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '658953bc-65ca-4703-b94c-e65cb4f518d4' : PortAllocation
                                allocate allocatedPort ::> 'CDT_System Project'::'CDT_System'::'Logical Architecture'::'Logical Functions'::'Root Logical Function'.'Helmet Receives a Hit'.'inActivity'
                                to allocatingPort ::> 'CDT_System Project'::'CDT_System'::'Logical Architecture'::'Structure'::'CDT System'.'Helmet Receives a Hit'.'CP 1'; 
                            ref allocation '7cae1e56-67ae-4cb8-99af-dd345f5450d8' : PortAllocation
                                allocate allocatedPort ::> 'CDT_System Project'::'CDT_System'::'Logical Architecture'::'Logical Functions'::'Root Logical Function'.'Receive Athlete '.'inHead '
                                to allocatingPort ::> 'CDT_System Project'::'CDT_System'::'Logical Architecture'::'Structure'::'CDT System'.'Helmet Receives a Hit'.'CP 1'; 
                            ref :>> providedInterfaces =  ('CDT_System Project'::'CDT_System'::'Logical Architecture'::'Interfaces'::'Athlete to Helmut'); 
                            ref :>> ownedPortAllocations =  ('CDT_System Project'::'CDT_System'::'Logical Architecture'::'Structure'::'CDT System'.'Helmet Receives a Hit'.'CP 1'.'658953bc-65ca-4703-b94c-e65cb4f518d4',
                            'CDT_System Project'::'CDT_System'::'Logical Architecture'::'Structure'::'CDT System'.'Helmet Receives a Hit'.'CP 1'.'7cae1e56-67ae-4cb8-99af-dd345f5450d8'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '2254f0b2-7fcb-4fff-9df9-9cc6e539c9c4' : PortAllocation
                                allocate allocatedPort ::> 'CDT_System Project'::'CDT_System'::'Logical Architecture'::'Logical Functions'::'Root Logical Function'.'Receive Athlete '.'outHelmut Motion'
                                to allocatingPort ::> 'CDT_System Project'::'CDT_System'::'Logical Architecture'::'Structure'::'CDT System'.'Helmet Receives a Hit'.'CP 2'; 
                            ref allocation 'ccb18095-9044-42e7-8970-eb718df6ad2c' : PortAllocation
                                allocate allocatedPort ::> 'CDT_System Project'::'CDT_System'::'Logical Architecture'::'Logical Functions'::'Root Logical Function'.'Helmet Receives a Hit'.'outHit'
                                to allocatingPort ::> 'CDT_System Project'::'CDT_System'::'Logical Architecture'::'Structure'::'CDT System'.'Helmet Receives a Hit'.'CP 2'; 
                            ref :>> ownedPortAllocations =  ('CDT_System Project'::'CDT_System'::'Logical Architecture'::'Structure'::'CDT System'.'Helmet Receives a Hit'.'CP 2'.'2254f0b2-7fcb-4fff-9df9-9cc6e539c9c4',
                            'CDT_System Project'::'CDT_System'::'Logical Architecture'::'Structure'::'CDT System'.'Helmet Receives a Hit'.'CP 2'.'ccb18095-9044-42e7-8970-eb718df6ad2c'); 
                            ref :>> requiredInterfaces =  ('CDT_System Project'::'CDT_System'::'Logical Architecture'::'Interfaces'::'Helmut to Sensing Device'); 
                        }  
                        ref :>> ownedFunctionalAllocation =  ('CDT_System Project'::'CDT_System'::'Logical Architecture'::'Structure'::'CDT System'.'Helmet Receives a Hit'.'eebdb447-be21-49c1-9bd6-2843c0c1300b',
                        'CDT_System Project'::'CDT_System'::'Logical Architecture'::'Structure'::'CDT System'.'Helmet Receives a Hit'.'a7381b8d-cba9-4b08-a0da-6e77187a3291',
                        'CDT_System Project'::'CDT_System'::'Logical Architecture'::'Structure'::'CDT System'.'Helmet Receives a Hit'.'5501b3fe-aee9-46de-8556-bb2704e5c054'); 
                    }  
                    part 'Sensing Device' : LogicalComponent { 
                        attribute :>> isAbstract = false; 
                        attribute :>> isActor = false; 
                        attribute :>> isHuman = false; 
                        allocation '31db90b8-4dc0-42d2-9811-1d46d989bc66' : ComponentFunctionalAllocation
                            allocate function ::> 'CDT_System Project'::'CDT_System'::'Logical Architecture'::'Logical Functions'::'Root Logical Function'.'Provide access to helmut mounting'
                            to component ::> 'CDT_System Project'::'CDT_System'::'Logical Architecture'::'Structure'::'CDT System'.'Sensing Device';
                        perform 'CDT_System Project'::'CDT_System'::'Logical Architecture'::'Logical Functions'::'Root Logical Function'.'Provide access to helmut mounting' ; 
                        allocation '44315f68-e064-4b53-94ff-d07073dafab9' : ComponentFunctionalAllocation
                            allocate function ::> 'CDT_System Project'::'CDT_System'::'Logical Architecture'::'Logical Functions'::'Root Logical Function'.'Enable Secure Collection'
                            to component ::> 'CDT_System Project'::'CDT_System'::'Logical Architecture'::'Structure'::'CDT System'.'Sensing Device';
                        perform 'CDT_System Project'::'CDT_System'::'Logical Architecture'::'Logical Functions'::'Root Logical Function'.'Enable Secure Collection' ; 
                        allocation 'e5d68de9-ba83-4eff-9922-6c8924e245f2' : ComponentFunctionalAllocation
                            allocate function ::> 'CDT_System Project'::'CDT_System'::'Logical Architecture'::'Logical Functions'::'Root Logical Function'.'Recieve ID'
                            to component ::> 'CDT_System Project'::'CDT_System'::'Logical Architecture'::'Structure'::'CDT System'.'Sensing Device';
                        perform 'CDT_System Project'::'CDT_System'::'Logical Architecture'::'Logical Functions'::'Root Logical Function'.'Recieve ID' ; 
                        allocation 'e962683a-6289-4321-9056-909774283fef' : ComponentFunctionalAllocation
                            allocate function ::> 'CDT_System Project'::'CDT_System'::'Logical Architecture'::'Logical Functions'::'Root Logical Function'.'Device records Hit'
                            to component ::> 'CDT_System Project'::'CDT_System'::'Logical Architecture'::'Structure'::'CDT System'.'Sensing Device';
                        perform 'CDT_System Project'::'CDT_System'::'Logical Architecture'::'Logical Functions'::'Root Logical Function'.'Device records Hit' ; 
                        allocation 'e59a19a3-e678-4203-9b4b-77cd4148c2af' : ComponentFunctionalAllocation
                            allocate function ::> 'CDT_System Project'::'CDT_System'::'Logical Architecture'::'Logical Functions'::'Root Logical Function'.'Device alerts possible Concussion'.'Send message'
                            to component ::> 'CDT_System Project'::'CDT_System'::'Logical Architecture'::'Structure'::'CDT System'.'Sensing Device';
                        perform 'CDT_System Project'::'CDT_System'::'Logical Architecture'::'Logical Functions'::'Root Logical Function'.'Device alerts possible Concussion'.'Send message' ; 
                        allocation '02b43269-ee61-4427-b329-0ed89bacfd58' : ComponentFunctionalAllocation
                            allocate function ::> 'CDT_System Project'::'CDT_System'::'Logical Architecture'::'Logical Functions'::'Root Logical Function'.'Data is Retrieved'.'Provide Hit Data'
                            to component ::> 'CDT_System Project'::'CDT_System'::'Logical Architecture'::'Structure'::'CDT System'.'Sensing Device';
                        perform 'CDT_System Project'::'CDT_System'::'Logical Architecture'::'Logical Functions'::'Root Logical Function'.'Data is Retrieved'.'Provide Hit Data' ; 
                        allocation '4adaa4ef-0e36-4848-9da5-18c210993806' : ComponentFunctionalAllocation
                            allocate function ::> 'CDT_System Project'::'CDT_System'::'Logical Architecture'::'Logical Functions'::'Root Logical Function'.'Enable Monitoring'.'Enable Monitoring'
                            to component ::> 'CDT_System Project'::'CDT_System'::'Logical Architecture'::'Structure'::'CDT System'.'Sensing Device';
                        perform 'CDT_System Project'::'CDT_System'::'Logical Architecture'::'Logical Functions'::'Root Logical Function'.'Enable Monitoring'.'Enable Monitoring' ; 
                        allocation '551e9e32-4c46-4fc5-acbe-89ed49669d4e' : ComponentFunctionalAllocation
                            allocate function ::> 'CDT_System Project'::'CDT_System'::'Logical Architecture'::'Logical Functions'::'Root Logical Function'.'Enable Monitoring'.'Look for bluetooth connect'
                            to component ::> 'CDT_System Project'::'CDT_System'::'Logical Architecture'::'Structure'::'CDT System'.'Sensing Device';
                        perform 'CDT_System Project'::'CDT_System'::'Logical Architecture'::'Logical Functions'::'Root Logical Function'.'Enable Monitoring'.'Look for bluetooth connect' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation 'cb05968f-62a1-41a8-b31c-bb5e7402be1b' : PortAllocation
                                allocate allocatedPort ::> 'CDT_System Project'::'CDT_System'::'Logical Architecture'::'Logical Functions'::'Root Logical Function'.'Enable Monitoring'.'Enable Monitoring'.'inHelmut Motion'
                                to allocatingPort ::> 'CDT_System Project'::'CDT_System'::'Logical Architecture'::'Structure'::'CDT System'.'Sensing Device'.'CP 1'; 
                            ref allocation 'e24fee8a-c71b-4b69-ae3c-375d3f9c6d93' : PortAllocation
                                allocate allocatedPort ::> 'CDT_System Project'::'CDT_System'::'Logical Architecture'::'Logical Functions'::'Root Logical Function'.'Device records Hit'.'inHit'
                                to allocatingPort ::> 'CDT_System Project'::'CDT_System'::'Logical Architecture'::'Structure'::'CDT System'.'Sensing Device'.'CP 1'; 
                            ref :>> providedInterfaces =  ('CDT_System Project'::'CDT_System'::'Logical Architecture'::'Interfaces'::'Helmut to Sensing Device'); 
                            ref :>> ownedPortAllocations =  ('CDT_System Project'::'CDT_System'::'Logical Architecture'::'Structure'::'CDT System'.'Sensing Device'.'CP 1'.'cb05968f-62a1-41a8-b31c-bb5e7402be1b',
                            'CDT_System Project'::'CDT_System'::'Logical Architecture'::'Structure'::'CDT System'.'Sensing Device'.'CP 1'.'e24fee8a-c71b-4b69-ae3c-375d3f9c6d93'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '126e1ea5-13a2-4374-883b-1e62a113020d' : PortAllocation
                                allocate allocatedPort ::> 'CDT_System Project'::'CDT_System'::'Logical Architecture'::'Logical Functions'::'Root Logical Function'.'Device alerts possible Concussion'.'Send message'.'FOP 1'
                                to allocatingPort ::> 'CDT_System Project'::'CDT_System'::'Logical Architecture'::'Structure'::'CDT System'.'Sensing Device'.'CP 2'; 
                            ref allocation '8d30e533-6a26-4176-93b3-34fe2258818e' : PortAllocation
                                allocate allocatedPort ::> 'CDT_System Project'::'CDT_System'::'Logical Architecture'::'Logical Functions'::'Root Logical Function'.'Enable Monitoring'.'Enable Monitoring'.'FOP 1'
                                to allocatingPort ::> 'CDT_System Project'::'CDT_System'::'Logical Architecture'::'Structure'::'CDT System'.'Sensing Device'.'CP 2'; 
                            ref :>> ownedPortAllocations =  ('CDT_System Project'::'CDT_System'::'Logical Architecture'::'Structure'::'CDT System'.'Sensing Device'.'CP 2'.'126e1ea5-13a2-4374-883b-1e62a113020d',
                            'CDT_System Project'::'CDT_System'::'Logical Architecture'::'Structure'::'CDT System'.'Sensing Device'.'CP 2'.'8d30e533-6a26-4176-93b3-34fe2258818e'); 
                            ref :>> requiredInterfaces =  ('CDT_System Project'::'CDT_System'::'Logical Architecture'::'Interfaces'::'SD to Lorawant'); 
                        }  
                        state 'StateMachine 1' : StateMachine  { 
                            attribute :>> isControlOperator = false; 
                            state 'Off' : Mode;  
                            state 'ON' : Mode { 
                                state 'ID Checking' : Mode { 
                                    ref :>> doActivity =  ('CDT_System Project'::'CDT_System'::'Logical Architecture'::'Logical Functions'::'Root Logical Function'.'Recieve ID'); 
                                }  
                                state 'IID Detected' : Mode { 
                                    ref :>> doActivity =  ('CDT_System Project'::'CDT_System'::'Logical Architecture'::'Logical Functions'::'Root Logical Function'.'Device records Hit',
                                    'CDT_System Project'::'CDT_System'::'Logical Architecture'::'Logical Functions'::'Root Logical Function'.'Device alerts possible Concussion'.'Send message',
                                    'CDT_System Project'::'CDT_System'::'Logical Architecture'::'Logical Functions'::'Root Logical Function'.'Data is Retrieved'.'Provide Hit Data',
                                    'CDT_System Project'::'CDT_System'::'Logical Architecture'::'Logical Functions'::'Root Logical Function'.'Enable Monitoring'.'Enable Monitoring',
                                    'CDT_System Project'::'CDT_System'::'Logical Architecture'::'Logical Functions'::'Root Logical Function'.'Enable Monitoring'.'Look for bluetooth connect'); 
                                }  
                                entry; then 'ID Checking';  
                                transition 'd6489613-4914-4925-9cc7-be751dd3f9b3' 
                                    first 'CDT_System Project'::'CDT_System'::'Logical Architecture'::'Structure'::'CDT System'.'Sensing Device'.'StateMachine 1'.'ON'.'ID Checking'
                                    accept 'Athlete ID' :> 'CDT_System Project'::'CDT_System'::'Operational Analysis'::'Data'::'Athlete ID'
                                    then 'CDT_System Project'::'CDT_System'::'Logical Architecture'::'Structure'::'CDT System'.'Sensing Device'.'StateMachine 1'.'ON'.'IID Detected' {
                                }  
                                ref :>> referencedStates =  ('CDT_System Project'::'CDT_System'::'Logical Architecture'::'Structure'::'CDT System'.'Sensing Device'.'StateMachine 1'.'ON'.'ID Checking',
                                'CDT_System Project'::'CDT_System'::'Logical Architecture'::'Structure'::'CDT System'.'Sensing Device'.'StateMachine 1'.'ON'.'IID Detected'); 
                            }  
                            transition '453ef859-7a00-49b4-a211-0599e129e061' 
                                first 'CDT_System Project'::'CDT_System'::'Logical Architecture'::'Structure'::'CDT System'.'Sensing Device'.'StateMachine 1'.'Off'
                                accept 'Power Applied' :> 'CDT_System Project'::'CDT_System'::'Operational Analysis'::'Data'::'Power Applied'
                                then 'CDT_System Project'::'CDT_System'::'Logical Architecture'::'Structure'::'CDT System'.'Sensing Device'.'StateMachine 1'.'ON' {
                            }  
                            entry; then 'Off';  
                        }  
                        ref :>> ownedFunctionalAllocation =  ('CDT_System Project'::'CDT_System'::'Logical Architecture'::'Structure'::'CDT System'.'Sensing Device'.'31db90b8-4dc0-42d2-9811-1d46d989bc66',
                        'CDT_System Project'::'CDT_System'::'Logical Architecture'::'Structure'::'CDT System'.'Sensing Device'.'44315f68-e064-4b53-94ff-d07073dafab9',
                        'CDT_System Project'::'CDT_System'::'Logical Architecture'::'Structure'::'CDT System'.'Sensing Device'.'e5d68de9-ba83-4eff-9922-6c8924e245f2',
                        'CDT_System Project'::'CDT_System'::'Logical Architecture'::'Structure'::'CDT System'.'Sensing Device'.'e962683a-6289-4321-9056-909774283fef',
                        'CDT_System Project'::'CDT_System'::'Logical Architecture'::'Structure'::'CDT System'.'Sensing Device'.'e59a19a3-e678-4203-9b4b-77cd4148c2af',
                        'CDT_System Project'::'CDT_System'::'Logical Architecture'::'Structure'::'CDT System'.'Sensing Device'.'02b43269-ee61-4427-b329-0ed89bacfd58',
                        'CDT_System Project'::'CDT_System'::'Logical Architecture'::'Structure'::'CDT System'.'Sensing Device'.'4adaa4ef-0e36-4848-9da5-18c210993806',
                        'CDT_System Project'::'CDT_System'::'Logical Architecture'::'Structure'::'CDT System'.'Sensing Device'.'551e9e32-4c46-4fc5-acbe-89ed49669d4e'); 
                        ref :>> ownedStateMachines =  ('CDT_System Project'::'CDT_System'::'Logical Architecture'::'Structure'::'CDT System'.'Sensing Device'.'StateMachine 1'); 
                    }  
                    part 'Lorawan' : LogicalComponent { 
                        attribute :>> isAbstract = false; 
                        attribute :>> isActor = false; 
                        attribute :>> isHuman = false; 
                        allocation '857d78d7-4fd7-453a-bcf3-4c61025cfb70' : ComponentFunctionalAllocation
                            allocate function ::> 'CDT_System Project'::'CDT_System'::'Logical Architecture'::'Logical Functions'::'Root Logical Function'.'Device alerts possible Concussion'.'Relay message'
                            to component ::> 'CDT_System Project'::'CDT_System'::'Logical Architecture'::'Structure'::'CDT System'.'Lorawan';
                        perform 'CDT_System Project'::'CDT_System'::'Logical Architecture'::'Logical Functions'::'Root Logical Function'.'Device alerts possible Concussion'.'Relay message' ; 
                        allocation '2dc09971-65b7-4714-a1fb-cf1b467a61b2' : ComponentFunctionalAllocation
                            allocate function ::> 'CDT_System Project'::'CDT_System'::'Logical Architecture'::'Logical Functions'::'Root Logical Function'.'653a1edf-a06b-472f-ac1d-98a95137cf8b'
                            to component ::> 'CDT_System Project'::'CDT_System'::'Logical Architecture'::'Structure'::'CDT System'.'Lorawan';
                        perform 'CDT_System Project'::'CDT_System'::'Logical Architecture'::'Logical Functions'::'Root Logical Function'.'653a1edf-a06b-472f-ac1d-98a95137cf8b' ; 
                        allocation '52fa01e5-9a24-40d2-83ab-0cfc565ea38a' : ComponentFunctionalAllocation
                            allocate function ::> 'CDT_System Project'::'CDT_System'::'Logical Architecture'::'Logical Functions'::'Root Logical Function'.'Enable Monitoring'.'Relay Enabled Message'
                            to component ::> 'CDT_System Project'::'CDT_System'::'Logical Architecture'::'Structure'::'CDT System'.'Lorawan';
                        perform 'CDT_System Project'::'CDT_System'::'Logical Architecture'::'Logical Functions'::'Root Logical Function'.'Enable Monitoring'.'Relay Enabled Message' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation 'dae1a1c5-a870-4089-8da8-39bcb97491d3' : PortAllocation
                                allocate allocatedPort ::> 'CDT_System Project'::'CDT_System'::'Logical Architecture'::'Logical Functions'::'Root Logical Function'.'Device alerts possible Concussion'.'Relay message'.'FIP 1'
                                to allocatingPort ::> 'CDT_System Project'::'CDT_System'::'Logical Architecture'::'Structure'::'CDT System'.'Lorawan'.'CP 1'; 
                            ref allocation '98d98175-7eab-44ac-bfeb-28879476bd15' : PortAllocation
                                allocate allocatedPort ::> 'CDT_System Project'::'CDT_System'::'Logical Architecture'::'Logical Functions'::'Root Logical Function'.'Enable Monitoring'.'Relay Enabled Message'.'FIP 1'
                                to allocatingPort ::> 'CDT_System Project'::'CDT_System'::'Logical Architecture'::'Structure'::'CDT System'.'Lorawan'.'CP 1'; 
                            ref :>> providedInterfaces =  ('CDT_System Project'::'CDT_System'::'Logical Architecture'::'Interfaces'::'SD to Lorawant'); 
                            ref :>> ownedPortAllocations =  ('CDT_System Project'::'CDT_System'::'Logical Architecture'::'Structure'::'CDT System'.'Lorawan'.'CP 1'.'dae1a1c5-a870-4089-8da8-39bcb97491d3',
                            'CDT_System Project'::'CDT_System'::'Logical Architecture'::'Structure'::'CDT System'.'Lorawan'.'CP 1'.'98d98175-7eab-44ac-bfeb-28879476bd15'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '8b768edd-aa74-4ec4-9594-599841589997' : PortAllocation
                                allocate allocatedPort ::> 'CDT_System Project'::'CDT_System'::'Logical Architecture'::'Logical Functions'::'Root Logical Function'.'Device alerts possible Concussion'.'Relay message'.'FOP 1'
                                to allocatingPort ::> 'CDT_System Project'::'CDT_System'::'Logical Architecture'::'Structure'::'CDT System'.'Lorawan'.'CP 2'; 
                            ref allocation '7d6051f1-4fcd-4929-a455-e3de38fc3661' : PortAllocation
                                allocate allocatedPort ::> 'CDT_System Project'::'CDT_System'::'Logical Architecture'::'Logical Functions'::'Root Logical Function'.'Enable Monitoring'.'Relay Enabled Message'.'FOP 1'
                                to allocatingPort ::> 'CDT_System Project'::'CDT_System'::'Logical Architecture'::'Structure'::'CDT System'.'Lorawan'.'CP 2'; 
                            ref :>> ownedPortAllocations =  ('CDT_System Project'::'CDT_System'::'Logical Architecture'::'Structure'::'CDT System'.'Lorawan'.'CP 2'.'8b768edd-aa74-4ec4-9594-599841589997',
                            'CDT_System Project'::'CDT_System'::'Logical Architecture'::'Structure'::'CDT System'.'Lorawan'.'CP 2'.'7d6051f1-4fcd-4929-a455-e3de38fc3661'); 
                            ref :>> requiredInterfaces =  ('CDT_System Project'::'CDT_System'::'Logical Architecture'::'Interfaces'::'Lora - SA'); 
                        }  
                        ref :>> ownedFunctionalAllocation =  ('CDT_System Project'::'CDT_System'::'Logical Architecture'::'Structure'::'CDT System'.'Lorawan'.'857d78d7-4fd7-453a-bcf3-4c61025cfb70',
                        'CDT_System Project'::'CDT_System'::'Logical Architecture'::'Structure'::'CDT System'.'Lorawan'.'2dc09971-65b7-4714-a1fb-cf1b467a61b2',
                        'CDT_System Project'::'CDT_System'::'Logical Architecture'::'Structure'::'CDT System'.'Lorawan'.'52fa01e5-9a24-40d2-83ab-0cfc565ea38a'); 
                    }  
                    part 'Network' : LogicalComponent { 
                        attribute :>> isAbstract = false; 
                        attribute :>> isActor = false; 
                        attribute :>> isHuman = false; 
                    }  
                    part 'CDT App' : LogicalComponent { 
                        attribute :>> isAbstract = false; 
                        attribute :>> isActor = false; 
                        attribute :>> isHuman = false; 
                        allocation 'a35c6a99-9ecc-4328-8e54-9c053379ad6a' : ComponentFunctionalAllocation
                            allocate function ::> 'CDT_System Project'::'CDT_System'::'Logical Architecture'::'Logical Functions'::'Root Logical Function'.'Device alerts possible Concussion'.'Alert the Training'
                            to component ::> 'CDT_System Project'::'CDT_System'::'Logical Architecture'::'Structure'::'CDT System'.'CDT App';
                        perform 'CDT_System Project'::'CDT_System'::'Logical Architecture'::'Logical Functions'::'Root Logical Function'.'Device alerts possible Concussion'.'Alert the Training' ; 
                        allocation '9516a526-2896-4cc4-8823-1ead314136d3' : ComponentFunctionalAllocation
                            allocate function ::> 'CDT_System Project'::'CDT_System'::'Logical Architecture'::'Logical Functions'::'Root Logical Function'.'Data is Retrieved'.'Intitate Data Retrieval'
                            to component ::> 'CDT_System Project'::'CDT_System'::'Logical Architecture'::'Structure'::'CDT System'.'CDT App';
                        perform 'CDT_System Project'::'CDT_System'::'Logical Architecture'::'Logical Functions'::'Root Logical Function'.'Data is Retrieved'.'Intitate Data Retrieval' ; 
                        allocation 'b02bab61-6953-4ee3-9d3b-615295f08cdb' : ComponentFunctionalAllocation
                            allocate function ::> 'CDT_System Project'::'CDT_System'::'Logical Architecture'::'Logical Functions'::'Root Logical Function'.'Data stored'.'Data is Presented'
                            to component ::> 'CDT_System Project'::'CDT_System'::'Logical Architecture'::'Structure'::'CDT System'.'CDT App';
                        perform 'CDT_System Project'::'CDT_System'::'Logical Architecture'::'Logical Functions'::'Root Logical Function'.'Data stored'.'Data is Presented' ; 
                        allocation '037f6d74-4993-4c33-b010-56ce403e7dfa' : ComponentFunctionalAllocation
                            allocate function ::> 'CDT_System Project'::'CDT_System'::'Logical Architecture'::'Logical Functions'::'Root Logical Function'.'Generates Reports'.'Request Report to be sent'
                            to component ::> 'CDT_System Project'::'CDT_System'::'Logical Architecture'::'Structure'::'CDT System'.'CDT App';
                        perform 'CDT_System Project'::'CDT_System'::'Logical Architecture'::'Logical Functions'::'Root Logical Function'.'Generates Reports'.'Request Report to be sent' ; 
                        allocation 'ca09b863-7ce5-4b9d-b21b-3a2ffd3b20ea' : ComponentFunctionalAllocation
                            allocate function ::> 'CDT_System Project'::'CDT_System'::'Logical Architecture'::'Logical Functions'::'Root Logical Function'.'Enable Monitoring'.'Enable Indicated'
                            to component ::> 'CDT_System Project'::'CDT_System'::'Logical Architecture'::'Structure'::'CDT System'.'CDT App';
                        perform 'CDT_System Project'::'CDT_System'::'Logical Architecture'::'Logical Functions'::'Root Logical Function'.'Enable Monitoring'.'Enable Indicated' ; 
                        allocation 'd205fce2-76d4-43f2-84a5-87f25a4cdd58' : ComponentFunctionalAllocation
                            allocate function ::> 'CDT_System Project'::'CDT_System'::'Logical Architecture'::'Logical Functions'::'Root Logical Function'.'Store Profile'.'Gather Profile Data'
                            to component ::> 'CDT_System Project'::'CDT_System'::'Logical Architecture'::'Structure'::'CDT System'.'CDT App';
                        perform 'CDT_System Project'::'CDT_System'::'Logical Architecture'::'Logical Functions'::'Root Logical Function'.'Store Profile'.'Gather Profile Data' ; 
                        allocation '957b0f96-eee4-4bd4-bdb2-4c2702f264dd' : ComponentFunctionalAllocation
                            allocate function ::> 'CDT_System Project'::'CDT_System'::'Logical Architecture'::'Logical Functions'::'Root Logical Function'.'Create Unique IDs for Athlete'.'Initiate ID Creation'
                            to component ::> 'CDT_System Project'::'CDT_System'::'Logical Architecture'::'Structure'::'CDT System'.'CDT App';
                        perform 'CDT_System Project'::'CDT_System'::'Logical Architecture'::'Logical Functions'::'Root Logical Function'.'Create Unique IDs for Athlete'.'Initiate ID Creation' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '30e633d9-b0bf-4058-981a-e0debd740bc9' : PortAllocation
                                allocate allocatedPort ::> 'CDT_System Project'::'CDT_System'::'Logical Architecture'::'Logical Functions'::'Root Logical Function'.'Device alerts possible Concussion'.'Alert the Training'.'FIP 1'
                                to allocatingPort ::> 'CDT_System Project'::'CDT_System'::'Logical Architecture'::'Structure'::'CDT System'.'CDT App'.'CP 1'; 
                            ref allocation 'fe007841-82c4-4cc9-921b-39aa4afe82cd' : PortAllocation
                                allocate allocatedPort ::> 'CDT_System Project'::'CDT_System'::'Logical Architecture'::'Logical Functions'::'Root Logical Function'.'Enable Monitoring'.'Enable Indicated'.'FIP 1'
                                to allocatingPort ::> 'CDT_System Project'::'CDT_System'::'Logical Architecture'::'Structure'::'CDT System'.'CDT App'.'CP 1'; 
                            ref allocation '664fee8f-8524-4d03-ab47-1a0b549a6a40' : PortAllocation
                                allocate allocatedPort ::> 'CDT_System Project'::'CDT_System'::'Logical Architecture'::'Logical Functions'::'Root Logical Function'.'Data stored'.'Data is Presented'.'FIP 1'
                                to allocatingPort ::> 'CDT_System Project'::'CDT_System'::'Logical Architecture'::'Structure'::'CDT System'.'CDT App'.'CP 1'; 
                            ref allocation '28617aa7-d46f-4413-b96c-e8391a5835c7' : PortAllocation
                                allocate allocatedPort ::> 'CDT_System Project'::'CDT_System'::'Logical Architecture'::'Logical Functions'::'Root Logical Function'.'Store Profile'.'Gather Profile Data'.'FOP 1'
                                to allocatingPort ::> 'CDT_System Project'::'CDT_System'::'Logical Architecture'::'Structure'::'CDT System'.'CDT App'.'CP 1'; 
                            ref allocation '45bf776b-33ed-4c6d-83bb-b32d88d60c37' : PortAllocation
                                allocate allocatedPort ::> 'CDT_System Project'::'CDT_System'::'Logical Architecture'::'Logical Functions'::'Root Logical Function'.'Create Unique IDs for Athlete'.'Initiate ID Creation'.'FOP 1'
                                to allocatingPort ::> 'CDT_System Project'::'CDT_System'::'Logical Architecture'::'Structure'::'CDT System'.'CDT App'.'CP 1'; 
                            ref allocation '311ccf7f-71c2-487f-b032-81dc32a99f1f' : PortAllocation
                                allocate allocatedPort ::> 'CDT_System Project'::'CDT_System'::'Logical Architecture'::'Logical Functions'::'Root Logical Function'.'Data is Retrieved'.'Intitate Data Retrieval'.'outRecorded Data'
                                to allocatingPort ::> 'CDT_System Project'::'CDT_System'::'Logical Architecture'::'Structure'::'CDT System'.'CDT App'.'CP 1'; 
                            ref allocation '546dca29-e08e-4b34-ba6a-4b98158ddefc' : PortAllocation
                                allocate allocatedPort ::> 'CDT_System Project'::'CDT_System'::'Logical Architecture'::'Logical Functions'::'Root Logical Function'.'Generates Reports'.'Request Report to be sent'.'FOP 1'
                                to allocatingPort ::> 'CDT_System Project'::'CDT_System'::'Logical Architecture'::'Structure'::'CDT System'.'CDT App'.'CP 1'; 
                            ref :>> providedInterfaces =  ('CDT_System Project'::'CDT_System'::'Logical Architecture'::'Interfaces'::'SA-CDT App'); 
                            ref :>> ownedPortAllocations =  ('CDT_System Project'::'CDT_System'::'Logical Architecture'::'Structure'::'CDT System'.'CDT App'.'CP 1'.'30e633d9-b0bf-4058-981a-e0debd740bc9',
                            'CDT_System Project'::'CDT_System'::'Logical Architecture'::'Structure'::'CDT System'.'CDT App'.'CP 1'.'fe007841-82c4-4cc9-921b-39aa4afe82cd',
                            'CDT_System Project'::'CDT_System'::'Logical Architecture'::'Structure'::'CDT System'.'CDT App'.'CP 1'.'664fee8f-8524-4d03-ab47-1a0b549a6a40',
                            'CDT_System Project'::'CDT_System'::'Logical Architecture'::'Structure'::'CDT System'.'CDT App'.'CP 1'.'28617aa7-d46f-4413-b96c-e8391a5835c7',
                            'CDT_System Project'::'CDT_System'::'Logical Architecture'::'Structure'::'CDT System'.'CDT App'.'CP 1'.'45bf776b-33ed-4c6d-83bb-b32d88d60c37',
                            'CDT_System Project'::'CDT_System'::'Logical Architecture'::'Structure'::'CDT System'.'CDT App'.'CP 1'.'311ccf7f-71c2-487f-b032-81dc32a99f1f',
                            'CDT_System Project'::'CDT_System'::'Logical Architecture'::'Structure'::'CDT System'.'CDT App'.'CP 1'.'546dca29-e08e-4b34-ba6a-4b98158ddefc'); 
                            ref :>> requiredInterfaces =  ('CDT_System Project'::'CDT_System'::'Logical Architecture'::'Interfaces'::'SA-CDT App'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '7f169efb-7dbe-4f5c-8a45-6a2c0647e3df' : PortAllocation
                                allocate allocatedPort ::> 'CDT_System Project'::'CDT_System'::'Logical Architecture'::'Logical Functions'::'Root Logical Function'.'Data stored'.'Data is Presented'.'outStored Data '
                                to allocatingPort ::> 'CDT_System Project'::'CDT_System'::'Logical Architecture'::'Structure'::'CDT System'.'CDT App'.'CP 2'; 
                            ref allocation '0e7b69a5-19db-456c-b8e9-fdeed7d0534d' : PortAllocation
                                allocate allocatedPort ::> 'CDT_System Project'::'CDT_System'::'Logical Architecture'::'Logical Functions'::'Root Logical Function'.'Enable Monitoring'.'Enable Indicated'.'outEnable Signal'
                                to allocatingPort ::> 'CDT_System Project'::'CDT_System'::'Logical Architecture'::'Structure'::'CDT System'.'CDT App'.'CP 2'; 
                            ref allocation 'e0625bce-7897-4700-be76-95abbfd3baa5' : PortAllocation
                                allocate allocatedPort ::> 'CDT_System Project'::'CDT_System'::'Logical Architecture'::'Logical Functions'::'Root Logical Function'.'Create Unique IDs for Athlete'.'Initiate ID Creation'.'inID'
                                to allocatingPort ::> 'CDT_System Project'::'CDT_System'::'Logical Architecture'::'Structure'::'CDT System'.'CDT App'.'CP 2'; 
                            ref allocation '9a3a3cac-7d65-4ea9-8a68-8154abec2294' : PortAllocation
                                allocate allocatedPort ::> 'CDT_System Project'::'CDT_System'::'Logical Architecture'::'Logical Functions'::'Root Logical Function'.'Device alerts possible Concussion'.'Alert the Training'.'outConcussion Alert to Trainer'
                                to allocatingPort ::> 'CDT_System Project'::'CDT_System'::'Logical Architecture'::'Structure'::'CDT System'.'CDT App'.'CP 2'; 
                            ref allocation '1410f370-6aa9-4484-9867-61c8244695d2' : PortAllocation
                                allocate allocatedPort ::> 'CDT_System Project'::'CDT_System'::'Logical Architecture'::'Logical Functions'::'Root Logical Function'.'Store Profile'.'Gather Profile Data'.'inAthlete Profile'
                                to allocatingPort ::> 'CDT_System Project'::'CDT_System'::'Logical Architecture'::'Structure'::'CDT System'.'CDT App'.'CP 2'; 
                            ref allocation '84b61141-5d54-4c7c-9143-9795e70a8f82' : PortAllocation
                                allocate allocatedPort ::> 'CDT_System Project'::'CDT_System'::'Logical Architecture'::'Logical Functions'::'Root Logical Function'.'Data is Retrieved'.'Intitate Data Retrieval'.'FIP 1'
                                to allocatingPort ::> 'CDT_System Project'::'CDT_System'::'Logical Architecture'::'Structure'::'CDT System'.'CDT App'.'CP 2'; 
                            ref allocation '74d2eaa0-acb8-4afb-8853-6411659d878a' : PortAllocation
                                allocate allocatedPort ::> 'CDT_System Project'::'CDT_System'::'Logical Architecture'::'Logical Functions'::'Root Logical Function'.'Generates Reports'.'Request Report to be sent'.'inExecute Policy'
                                to allocatingPort ::> 'CDT_System Project'::'CDT_System'::'Logical Architecture'::'Structure'::'CDT System'.'CDT App'.'CP 2'; 
                            ref :>> providedInterfaces =  ('CDT_System Project'::'CDT_System'::'Logical Architecture'::'Interfaces'::'CDT App - T'); 
                            ref :>> ownedPortAllocations =  ('CDT_System Project'::'CDT_System'::'Logical Architecture'::'Structure'::'CDT System'.'CDT App'.'CP 2'.'7f169efb-7dbe-4f5c-8a45-6a2c0647e3df',
                            'CDT_System Project'::'CDT_System'::'Logical Architecture'::'Structure'::'CDT System'.'CDT App'.'CP 2'.'0e7b69a5-19db-456c-b8e9-fdeed7d0534d',
                            'CDT_System Project'::'CDT_System'::'Logical Architecture'::'Structure'::'CDT System'.'CDT App'.'CP 2'.'e0625bce-7897-4700-be76-95abbfd3baa5',
                            'CDT_System Project'::'CDT_System'::'Logical Architecture'::'Structure'::'CDT System'.'CDT App'.'CP 2'.'9a3a3cac-7d65-4ea9-8a68-8154abec2294',
                            'CDT_System Project'::'CDT_System'::'Logical Architecture'::'Structure'::'CDT System'.'CDT App'.'CP 2'.'1410f370-6aa9-4484-9867-61c8244695d2',
                            'CDT_System Project'::'CDT_System'::'Logical Architecture'::'Structure'::'CDT System'.'CDT App'.'CP 2'.'84b61141-5d54-4c7c-9143-9795e70a8f82',
                            'CDT_System Project'::'CDT_System'::'Logical Architecture'::'Structure'::'CDT System'.'CDT App'.'CP 2'.'74d2eaa0-acb8-4afb-8853-6411659d878a'); 
                            ref :>> requiredInterfaces =  ('CDT_System Project'::'CDT_System'::'Logical Architecture'::'Interfaces'::'CDT App - T'); 
                        }  
                        port 'CP 3' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation 'c1c2511f-2ab2-40ee-8ec9-a1f3b408a879' : PortAllocation
                                allocate allocatedPort ::> 'CDT_System Project'::'CDT_System'::'Logical Architecture'::'Logical Functions'::'Root Logical Function'.'Data is Retrieved'.'Intitate Data Retrieval'.'FOP 1'
                                to allocatingPort ::> 'CDT_System Project'::'CDT_System'::'Logical Architecture'::'Structure'::'CDT System'.'CDT App'.'CP 3'; 
                            ref allocation '7914fdc0-6cf2-4b96-b2ff-461482769290' : PortAllocation
                                allocate allocatedPort ::> 'CDT_System Project'::'CDT_System'::'Logical Architecture'::'Logical Functions'::'Root Logical Function'.'Enable Monitoring'.'Enable Indicated'.'FOP 2'
                                to allocatingPort ::> 'CDT_System Project'::'CDT_System'::'Logical Architecture'::'Structure'::'CDT System'.'CDT App'.'CP 3'; 
                            ref :>> ownedPortAllocations =  ('CDT_System Project'::'CDT_System'::'Logical Architecture'::'Structure'::'CDT System'.'CDT App'.'CP 3'.'c1c2511f-2ab2-40ee-8ec9-a1f3b408a879',
                            'CDT_System Project'::'CDT_System'::'Logical Architecture'::'Structure'::'CDT System'.'CDT App'.'CP 3'.'7914fdc0-6cf2-4b96-b2ff-461482769290'); 
                            ref :>> requiredInterfaces =  ('CDT_System Project'::'CDT_System'::'Logical Architecture'::'Interfaces'::'BT - CDTApp'); 
                        }  
                        ref :>> ownedFunctionalAllocation =  ('CDT_System Project'::'CDT_System'::'Logical Architecture'::'Structure'::'CDT System'.'CDT App'.'a35c6a99-9ecc-4328-8e54-9c053379ad6a',
                        'CDT_System Project'::'CDT_System'::'Logical Architecture'::'Structure'::'CDT System'.'CDT App'.'9516a526-2896-4cc4-8823-1ead314136d3',
                        'CDT_System Project'::'CDT_System'::'Logical Architecture'::'Structure'::'CDT System'.'CDT App'.'b02bab61-6953-4ee3-9d3b-615295f08cdb',
                        'CDT_System Project'::'CDT_System'::'Logical Architecture'::'Structure'::'CDT System'.'CDT App'.'037f6d74-4993-4c33-b010-56ce403e7dfa',
                        'CDT_System Project'::'CDT_System'::'Logical Architecture'::'Structure'::'CDT System'.'CDT App'.'ca09b863-7ce5-4b9d-b21b-3a2ffd3b20ea',
                        'CDT_System Project'::'CDT_System'::'Logical Architecture'::'Structure'::'CDT System'.'CDT App'.'d205fce2-76d4-43f2-84a5-87f25a4cdd58',
                        'CDT_System Project'::'CDT_System'::'Logical Architecture'::'Structure'::'CDT System'.'CDT App'.'957b0f96-eee4-4bd4-bdb2-4c2702f264dd'); 
                    }  
                    part 'Bluetooth' : LogicalComponent { 
                        attribute :>> isAbstract = false; 
                        attribute :>> isActor = false; 
                        attribute :>> isHuman = false; 
                        allocation '30fd67ab-89de-4156-bd68-775cc8eeb38f' : ComponentFunctionalAllocation
                            allocate function ::> 'CDT_System Project'::'CDT_System'::'Logical Architecture'::'Logical Functions'::'Root Logical Function'.'Data is Retrieved'.'Request the Data '
                            to component ::> 'CDT_System Project'::'CDT_System'::'Logical Architecture'::'Structure'::'CDT System'.'Bluetooth';
                        perform 'CDT_System Project'::'CDT_System'::'Logical Architecture'::'Logical Functions'::'Root Logical Function'.'Data is Retrieved'.'Request the Data ' ; 
                        allocation 'f729d437-6f87-4efe-8d23-b06fc9c57120' : ComponentFunctionalAllocation
                            allocate function ::> 'CDT_System Project'::'CDT_System'::'Logical Architecture'::'Logical Functions'::'Root Logical Function'.'Enable Monitoring'.'Enable Bluetoth Connect'
                            to component ::> 'CDT_System Project'::'CDT_System'::'Logical Architecture'::'Structure'::'CDT System'.'Bluetooth';
                        perform 'CDT_System Project'::'CDT_System'::'Logical Architecture'::'Logical Functions'::'Root Logical Function'.'Enable Monitoring'.'Enable Bluetoth Connect' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'f3e20335-de86-4e30-af27-0c42f58ff88b' : PortAllocation
                                allocate allocatedPort ::> 'CDT_System Project'::'CDT_System'::'Logical Architecture'::'Logical Functions'::'Root Logical Function'.'Data is Retrieved'.'Request the Data '.'FIP 1'
                                to allocatingPort ::> 'CDT_System Project'::'CDT_System'::'Logical Architecture'::'Structure'::'CDT System'.'Bluetooth'.'CP 1'; 
                            ref allocation '63a273cf-63f4-4705-9c5b-f24116f27b42' : PortAllocation
                                allocate allocatedPort ::> 'CDT_System Project'::'CDT_System'::'Logical Architecture'::'Logical Functions'::'Root Logical Function'.'Enable Monitoring'.'Enable Bluetoth Connect'.'FIP 1'
                                to allocatingPort ::> 'CDT_System Project'::'CDT_System'::'Logical Architecture'::'Structure'::'CDT System'.'Bluetooth'.'CP 1'; 
                            ref :>> providedInterfaces =  ('CDT_System Project'::'CDT_System'::'Logical Architecture'::'Interfaces'::'BT - CDTApp'); 
                            ref :>> ownedPortAllocations =  ('CDT_System Project'::'CDT_System'::'Logical Architecture'::'Structure'::'CDT System'.'Bluetooth'.'CP 1'.'f3e20335-de86-4e30-af27-0c42f58ff88b',
                            'CDT_System Project'::'CDT_System'::'Logical Architecture'::'Structure'::'CDT System'.'Bluetooth'.'CP 1'.'63a273cf-63f4-4705-9c5b-f24116f27b42'); 
                        }  
                        ref :>> ownedFunctionalAllocation =  ('CDT_System Project'::'CDT_System'::'Logical Architecture'::'Structure'::'CDT System'.'Bluetooth'.'30fd67ab-89de-4156-bd68-775cc8eeb38f',
                        'CDT_System Project'::'CDT_System'::'Logical Architecture'::'Structure'::'CDT System'.'Bluetooth'.'f729d437-6f87-4efe-8d23-b06fc9c57120'); 
                    }  
                    allocation 'ff901613-8144-4da9-9e26-a97e40067ae8' : ComponentFunctionalAllocation
                        allocate function ::> 'CDT_System Project'::'CDT_System'::'Logical Architecture'::'Logical Functions'::'Root Logical Function'.'Device'
                        to component ::> 'CDT_System Project'::'CDT_System'::'Logical Architecture'::'Structure'::'CDT System';
                    perform 'CDT_System Project'::'CDT_System'::'Logical Architecture'::'Logical Functions'::'Root Logical Function'.'Device' ; 
                    interface '72474429-4604-476c-b55b-c5969cb59c2e' : ComponentExchange 
                        connect source ::> 'CDT_System Project'::'CDT_System'::'Logical Architecture'::'Structure'::'CDT System'.'Helmet Receives a Hit'.'CP 2'
                        to  target ::> 'CDT_System Project'::'CDT_System'::'Logical Architecture'::'Structure'::'CDT System'.'Sensing Device'.'CP 1' { 
                        attribute :>> isOriented = false; 
                        attribute :>> interfaceName = "Helmut to Sensing Device"; 
                        attribute :>> kind = ComponentExchangeKind::FLOW; 
                        allocation 'a9facac1-11e9-419d-b292-d552e592ab84' : ComponentExchangeFunctionalExchangeAllocation
                            allocate functionalExchange ::> 'CDT_System Project'::'CDT_System'::'Logical Architecture'::'Logical Functions'::'Root Logical Function'.'56e3f648-295a-488f-b3d0-b6c6fd35f619'
                            to componentExchange ::> 'CDT_System Project'::'CDT_System'::'Logical Architecture'::'Structure'::'CDT System'.'72474429-4604-476c-b55b-c5969cb59c2e'; 
                        allocation '60d25ace-4080-450b-a934-51b2b93b4b13' : ComponentExchangeFunctionalExchangeAllocation
                            allocate functionalExchange ::> 'CDT_System Project'::'CDT_System'::'Logical Architecture'::'Logical Functions'::'Root Logical Function'.'68e7ee56-30a5-4c17-8bfb-5309173b9a78'
                            to componentExchange ::> 'CDT_System Project'::'CDT_System'::'Logical Architecture'::'Structure'::'CDT System'.'72474429-4604-476c-b55b-c5969cb59c2e'; 
                        ref :>> ownedComponentExchangeFunctionalExchangeAllocations =  ('CDT_System Project'::'CDT_System'::'Logical Architecture'::'Structure'::'CDT System'.'72474429-4604-476c-b55b-c5969cb59c2e'.'a9facac1-11e9-419d-b292-d552e592ab84',
                        'CDT_System Project'::'CDT_System'::'Logical Architecture'::'Structure'::'CDT System'.'72474429-4604-476c-b55b-c5969cb59c2e'.'60d25ace-4080-450b-a934-51b2b93b4b13'); 
                    }  
                    interface 'f28751f1-1ef8-4aa9-a079-a35053f18e4d' : ComponentExchange 
                        connect source ::> 'CDT_System Project'::'CDT_System'::'Logical Architecture'::'Structure'::'CDT System'.'Sensing Device'.'CP 2'
                        to  target ::> 'CDT_System Project'::'CDT_System'::'Logical Architecture'::'Structure'::'CDT System'.'Lorawan'.'CP 1' { 
                        attribute :>> isOriented = false; 
                        attribute :>> interfaceName = "SD to Lorawant"; 
                        attribute :>> kind = ComponentExchangeKind::FLOW; 
                        allocation '4de07133-74e7-4e96-832c-99df7d778795' : ComponentExchangeFunctionalExchangeAllocation
                            allocate functionalExchange ::> 'CDT_System Project'::'CDT_System'::'Logical Architecture'::'Logical Functions'::'Root Logical Function'.'Device alerts possible Concussion'.'2ad3591e-5a1b-458d-be75-1a6f8a8b6aed'
                            to componentExchange ::> 'CDT_System Project'::'CDT_System'::'Logical Architecture'::'Structure'::'CDT System'.'f28751f1-1ef8-4aa9-a079-a35053f18e4d'; 
                        allocation 'beb52847-7223-43d5-8d7a-53ff27410b3b' : ComponentExchangeFunctionalExchangeAllocation
                            allocate functionalExchange ::> 'CDT_System Project'::'CDT_System'::'Logical Architecture'::'Logical Functions'::'Root Logical Function'.'Enable Monitoring'.'ed518be9-43ff-4d81-b589-3a8c39857811'
                            to componentExchange ::> 'CDT_System Project'::'CDT_System'::'Logical Architecture'::'Structure'::'CDT System'.'f28751f1-1ef8-4aa9-a079-a35053f18e4d'; 
                        ref :>> ownedComponentExchangeFunctionalExchangeAllocations =  ('CDT_System Project'::'CDT_System'::'Logical Architecture'::'Structure'::'CDT System'.'f28751f1-1ef8-4aa9-a079-a35053f18e4d'.'4de07133-74e7-4e96-832c-99df7d778795',
                        'CDT_System Project'::'CDT_System'::'Logical Architecture'::'Structure'::'CDT System'.'f28751f1-1ef8-4aa9-a079-a35053f18e4d'.'beb52847-7223-43d5-8d7a-53ff27410b3b'); 
                    }  
                    interface 'b8909acf-95c7-498a-acef-3cbfe7cb217d' : ComponentExchange 
                        connect source ::> 'CDT_System Project'::'CDT_System'::'Logical Architecture'::'Structure'::'CDT System'.'Lorawan'.'CP 2'
                        to  target ::> 'CDT_System Project'::'CDT_System'::'Logical Architecture'::'Structure'::'CDT System'.'Secure Application'.'CP 1' { 
                        attribute :>> isOriented = false; 
                        attribute :>> interfaceName = "Lora - SA"; 
                        attribute :>> kind = ComponentExchangeKind::FLOW; 
                        allocation 'e44dcc21-36ca-48d7-8f73-799234f0137f' : ComponentExchangeFunctionalExchangeAllocation
                            allocate functionalExchange ::> 'CDT_System Project'::'CDT_System'::'Logical Architecture'::'Logical Functions'::'Root Logical Function'.'Device alerts possible Concussion'.'45077ed7-3532-4a54-983a-4472bf80b75f'
                            to componentExchange ::> 'CDT_System Project'::'CDT_System'::'Logical Architecture'::'Structure'::'CDT System'.'b8909acf-95c7-498a-acef-3cbfe7cb217d'; 
                        allocation '5cd8aa0b-697c-4471-a490-93c213499d6f' : ComponentExchangeFunctionalExchangeAllocation
                            allocate functionalExchange ::> 'CDT_System Project'::'CDT_System'::'Logical Architecture'::'Logical Functions'::'Root Logical Function'.'Enable Monitoring'.'346ba0de-117f-4838-bd24-1b822d200e79'
                            to componentExchange ::> 'CDT_System Project'::'CDT_System'::'Logical Architecture'::'Structure'::'CDT System'.'b8909acf-95c7-498a-acef-3cbfe7cb217d'; 
                        ref :>> ownedComponentExchangeFunctionalExchangeAllocations =  ('CDT_System Project'::'CDT_System'::'Logical Architecture'::'Structure'::'CDT System'.'b8909acf-95c7-498a-acef-3cbfe7cb217d'.'e44dcc21-36ca-48d7-8f73-799234f0137f',
                        'CDT_System Project'::'CDT_System'::'Logical Architecture'::'Structure'::'CDT System'.'b8909acf-95c7-498a-acef-3cbfe7cb217d'.'5cd8aa0b-697c-4471-a490-93c213499d6f'); 
                    }  
                    interface '71336acd-8612-426a-a43e-a50cca5d1561' : ComponentExchange 
                        connect source ::> 'CDT_System Project'::'CDT_System'::'Logical Architecture'::'Structure'::'CDT System'.'Secure Application'.'CP 2'
                        to  target ::> 'CDT_System Project'::'CDT_System'::'Logical Architecture'::'Structure'::'CDT System'.'CDT App'.'CP 1' { 
                        attribute :>> isOriented = false; 
                        attribute :>> interfaceName = "SA-CDT App"; 
                        attribute :>> kind = ComponentExchangeKind::FLOW; 
                        allocation '3304214e-40d9-4ff3-b50b-715294a25157' : ComponentExchangeFunctionalExchangeAllocation
                            allocate functionalExchange ::> 'CDT_System Project'::'CDT_System'::'Logical Architecture'::'Logical Functions'::'Root Logical Function'.'Device alerts possible Concussion'.'d194214f-1ab1-443a-97ab-38dc1fe35d02'
                            to componentExchange ::> 'CDT_System Project'::'CDT_System'::'Logical Architecture'::'Structure'::'CDT System'.'71336acd-8612-426a-a43e-a50cca5d1561'; 
                        allocation 'f7ffa1a4-6f93-4b98-9dd3-3a141059eec1' : ComponentExchangeFunctionalExchangeAllocation
                            allocate functionalExchange ::> 'CDT_System Project'::'CDT_System'::'Logical Architecture'::'Logical Functions'::'Root Logical Function'.'Enable Monitoring'.'6bc089b3-336d-4890-a903-ab77f625b6e0'
                            to componentExchange ::> 'CDT_System Project'::'CDT_System'::'Logical Architecture'::'Structure'::'CDT System'.'71336acd-8612-426a-a43e-a50cca5d1561'; 
                        allocation '8407f4e1-d9d6-42ab-93be-069bb542e153' : ComponentExchangeFunctionalExchangeAllocation
                            allocate functionalExchange ::> 'CDT_System Project'::'CDT_System'::'Logical Architecture'::'Logical Functions'::'Root Logical Function'.'Data stored'.'062e99f3-77a8-4aff-8249-e8b8a460a254'
                            to componentExchange ::> 'CDT_System Project'::'CDT_System'::'Logical Architecture'::'Structure'::'CDT System'.'71336acd-8612-426a-a43e-a50cca5d1561'; 
                        allocation '6b28316e-5d3b-4783-a6fc-a20fbf6aa7fb' : ComponentExchangeFunctionalExchangeAllocation
                            allocate functionalExchange ::> 'CDT_System Project'::'CDT_System'::'Logical Architecture'::'Logical Functions'::'Root Logical Function'.'Store Profile'.'4614f066-5aa3-4b81-a308-99d5a57d3889'
                            to componentExchange ::> 'CDT_System Project'::'CDT_System'::'Logical Architecture'::'Structure'::'CDT System'.'71336acd-8612-426a-a43e-a50cca5d1561'; 
                        allocation '3d82ea3e-a972-49b4-8f4f-22792aa2d45f' : ComponentExchangeFunctionalExchangeAllocation
                            allocate functionalExchange ::> 'CDT_System Project'::'CDT_System'::'Logical Architecture'::'Logical Functions'::'Root Logical Function'.'Create Unique IDs for Athlete'.'5c40769b-d826-496b-894d-6efeb8a0a5b5'
                            to componentExchange ::> 'CDT_System Project'::'CDT_System'::'Logical Architecture'::'Structure'::'CDT System'.'71336acd-8612-426a-a43e-a50cca5d1561'; 
                        allocation '91440aab-4e8e-4379-8a47-6b9df4df9aa5' : ComponentExchangeFunctionalExchangeAllocation
                            allocate functionalExchange ::> 'CDT_System Project'::'CDT_System'::'Logical Architecture'::'Logical Functions'::'Root Logical Function'.'71992433-b730-4c78-b2c6-634c4f622ff2'
                            to componentExchange ::> 'CDT_System Project'::'CDT_System'::'Logical Architecture'::'Structure'::'CDT System'.'71336acd-8612-426a-a43e-a50cca5d1561'; 
                        allocation 'b0ff392c-b92f-4328-9764-23f5b858de19' : ComponentExchangeFunctionalExchangeAllocation
                            allocate functionalExchange ::> 'CDT_System Project'::'CDT_System'::'Logical Architecture'::'Logical Functions'::'Root Logical Function'.'Generates Reports'.'a968678a-bdee-4cc3-8a24-1cd23df515a3'
                            to componentExchange ::> 'CDT_System Project'::'CDT_System'::'Logical Architecture'::'Structure'::'CDT System'.'71336acd-8612-426a-a43e-a50cca5d1561'; 
                        ref :>> ownedComponentExchangeFunctionalExchangeAllocations =  ('CDT_System Project'::'CDT_System'::'Logical Architecture'::'Structure'::'CDT System'.'71336acd-8612-426a-a43e-a50cca5d1561'.'3304214e-40d9-4ff3-b50b-715294a25157',
                        'CDT_System Project'::'CDT_System'::'Logical Architecture'::'Structure'::'CDT System'.'71336acd-8612-426a-a43e-a50cca5d1561'.'f7ffa1a4-6f93-4b98-9dd3-3a141059eec1',
                        'CDT_System Project'::'CDT_System'::'Logical Architecture'::'Structure'::'CDT System'.'71336acd-8612-426a-a43e-a50cca5d1561'.'8407f4e1-d9d6-42ab-93be-069bb542e153',
                        'CDT_System Project'::'CDT_System'::'Logical Architecture'::'Structure'::'CDT System'.'71336acd-8612-426a-a43e-a50cca5d1561'.'6b28316e-5d3b-4783-a6fc-a20fbf6aa7fb',
                        'CDT_System Project'::'CDT_System'::'Logical Architecture'::'Structure'::'CDT System'.'71336acd-8612-426a-a43e-a50cca5d1561'.'3d82ea3e-a972-49b4-8f4f-22792aa2d45f',
                        'CDT_System Project'::'CDT_System'::'Logical Architecture'::'Structure'::'CDT System'.'71336acd-8612-426a-a43e-a50cca5d1561'.'91440aab-4e8e-4379-8a47-6b9df4df9aa5',
                        'CDT_System Project'::'CDT_System'::'Logical Architecture'::'Structure'::'CDT System'.'71336acd-8612-426a-a43e-a50cca5d1561'.'b0ff392c-b92f-4328-9764-23f5b858de19'); 
                    }  
                    interface '1a78bd51-6f84-42bf-99ce-36c157a7fb92' : ComponentExchange 
                        connect source ::> 'CDT_System Project'::'CDT_System'::'Logical Architecture'::'Structure'::'CDT System'.'Bluetooth'.'CP 1'
                        to  target ::> 'CDT_System Project'::'CDT_System'::'Logical Architecture'::'Structure'::'CDT System'.'CDT App'.'CP 3' { 
                        attribute :>> isOriented = false; 
                        attribute :>> interfaceName = "BT - CDTApp"; 
                        attribute :>> kind = ComponentExchangeKind::FLOW; 
                        allocation 'fd5c6220-a16a-487a-ad0e-11faf0770392' : ComponentExchangeFunctionalExchangeAllocation
                            allocate functionalExchange ::> 'CDT_System Project'::'CDT_System'::'Logical Architecture'::'Logical Functions'::'Root Logical Function'.'Data is Retrieved'.'c667cdb0-6ba8-4c8d-b6aa-52cec107730e'
                            to componentExchange ::> 'CDT_System Project'::'CDT_System'::'Logical Architecture'::'Structure'::'CDT System'.'1a78bd51-6f84-42bf-99ce-36c157a7fb92'; 
                        allocation 'f2ddfc54-c993-4d13-94e6-fd2984944e12' : ComponentExchangeFunctionalExchangeAllocation
                            allocate functionalExchange ::> 'CDT_System Project'::'CDT_System'::'Logical Architecture'::'Logical Functions'::'Root Logical Function'.'Enable Monitoring'.'2c13b94c-54bc-4937-b982-6e5870f616af'
                            to componentExchange ::> 'CDT_System Project'::'CDT_System'::'Logical Architecture'::'Structure'::'CDT System'.'1a78bd51-6f84-42bf-99ce-36c157a7fb92'; 
                        ref :>> ownedComponentExchangeFunctionalExchangeAllocations =  ('CDT_System Project'::'CDT_System'::'Logical Architecture'::'Structure'::'CDT System'.'1a78bd51-6f84-42bf-99ce-36c157a7fb92'.'fd5c6220-a16a-487a-ad0e-11faf0770392',
                        'CDT_System Project'::'CDT_System'::'Logical Architecture'::'Structure'::'CDT System'.'1a78bd51-6f84-42bf-99ce-36c157a7fb92'.'f2ddfc54-c993-4d13-94e6-fd2984944e12'); 
                    }  
                    ref :>> ownedLogicalComponents =  ('CDT_System Project'::'CDT_System'::'Logical Architecture'::'Structure'::'CDT System'.'Secure Application',
                    'CDT_System Project'::'CDT_System'::'Logical Architecture'::'Structure'::'CDT System'.'ID Device',
                    'CDT_System Project'::'CDT_System'::'Logical Architecture'::'Structure'::'CDT System'.'Helmet Receives a Hit',
                    'CDT_System Project'::'CDT_System'::'Logical Architecture'::'Structure'::'CDT System'.'Sensing Device',
                    'CDT_System Project'::'CDT_System'::'Logical Architecture'::'Structure'::'CDT System'.'Lorawan',
                    'CDT_System Project'::'CDT_System'::'Logical Architecture'::'Structure'::'CDT System'.'Network',
                    'CDT_System Project'::'CDT_System'::'Logical Architecture'::'Structure'::'CDT System'.'CDT App',
                    'CDT_System Project'::'CDT_System'::'Logical Architecture'::'Structure'::'CDT System'.'Bluetooth'); 
                    ref :>> ownedFunctionalAllocation =  ('CDT_System Project'::'CDT_System'::'Logical Architecture'::'Structure'::'CDT System'.'ff901613-8144-4da9-9e26-a97e40067ae8'); 
                    ref :>> ownedComponentExchanges =  ('CDT_System Project'::'CDT_System'::'Logical Architecture'::'Structure'::'CDT System'.'72474429-4604-476c-b55b-c5969cb59c2e',
                    'CDT_System Project'::'CDT_System'::'Logical Architecture'::'Structure'::'CDT System'.'f28751f1-1ef8-4aa9-a079-a35053f18e4d',
                    'CDT_System Project'::'CDT_System'::'Logical Architecture'::'Structure'::'CDT System'.'b8909acf-95c7-498a-acef-3cbfe7cb217d',
                    'CDT_System Project'::'CDT_System'::'Logical Architecture'::'Structure'::'CDT System'.'71336acd-8612-426a-a43e-a50cca5d1561',
                    'CDT_System Project'::'CDT_System'::'Logical Architecture'::'Structure'::'CDT System'.'1a78bd51-6f84-42bf-99ce-36c157a7fb92'); 
                     
                }  
                part 'Trainer' : LogicalComponent { 
                    attribute :>> isAbstract = false; 
                    attribute :>> isActor = true; 
                    attribute :>> isHuman = false; 
                    allocation '0dcfab07-febd-4a99-aafb-ee9e52837803' : ComponentFunctionalAllocation
                        allocate function ::> 'CDT_System Project'::'CDT_System'::'Logical Architecture'::'Logical Functions'::'Root Logical Function'.'Create profiles for Athletes'
                        to component ::> 'CDT_System Project'::'CDT_System'::'Logical Architecture'::'Structure'::'Trainer';
                    perform 'CDT_System Project'::'CDT_System'::'Logical Architecture'::'Logical Functions'::'Root Logical Function'.'Create profiles for Athletes' ; 
                    allocation 'd68208c0-4e6f-477d-b830-8393f9adbc71' : ComponentFunctionalAllocation
                        allocate function ::> 'CDT_System Project'::'CDT_System'::'Logical Architecture'::'Logical Functions'::'Root Logical Function'.'Create Unique IDs'
                        to component ::> 'CDT_System Project'::'CDT_System'::'Logical Architecture'::'Structure'::'Trainer';
                    perform 'CDT_System Project'::'CDT_System'::'Logical Architecture'::'Logical Functions'::'Root Logical Function'.'Create Unique IDs' ; 
                    allocation '6bed8a2d-e5e1-46f5-8a49-9859f2a4d36a' : ComponentFunctionalAllocation
                        allocate function ::> 'CDT_System Project'::'CDT_System'::'Logical Architecture'::'Logical Functions'::'Root Logical Function'.'Provide ID to Athlete'
                        to component ::> 'CDT_System Project'::'CDT_System'::'Logical Architecture'::'Structure'::'Trainer';
                    perform 'CDT_System Project'::'CDT_System'::'Logical Architecture'::'Logical Functions'::'Root Logical Function'.'Provide ID to Athlete' ; 
                    allocation 'd0732047-b6f2-4f18-921b-257dcd71210f' : ComponentFunctionalAllocation
                        allocate function ::> 'CDT_System Project'::'CDT_System'::'Logical Architecture'::'Logical Functions'::'Root Logical Function'.'Assemble System Components'
                        to component ::> 'CDT_System Project'::'CDT_System'::'Logical Architecture'::'Structure'::'Trainer';
                    perform 'CDT_System Project'::'CDT_System'::'Logical Architecture'::'Logical Functions'::'Root Logical Function'.'Assemble System Components' ; 
                    allocation 'e160c59f-38b8-4cb2-b9f0-b9089bb6ec28' : ComponentFunctionalAllocation
                        allocate function ::> 'CDT_System Project'::'CDT_System'::'Logical Architecture'::'Logical Functions'::'Root Logical Function'.'Prep the device for use'
                        to component ::> 'CDT_System Project'::'CDT_System'::'Logical Architecture'::'Structure'::'Trainer';
                    perform 'CDT_System Project'::'CDT_System'::'Logical Architecture'::'Logical Functions'::'Root Logical Function'.'Prep the device for use' ; 
                    allocation 'b360201e-a359-4f59-a537-7d90dcca838c' : ComponentFunctionalAllocation
                        allocate function ::> 'CDT_System Project'::'CDT_System'::'Logical Architecture'::'Logical Functions'::'Root Logical Function'.'Recieve Enabled Signal from Athelete Helmut'
                        to component ::> 'CDT_System Project'::'CDT_System'::'Logical Architecture'::'Structure'::'Trainer';
                    perform 'CDT_System Project'::'CDT_System'::'Logical Architecture'::'Logical Functions'::'Root Logical Function'.'Recieve Enabled Signal from Athelete Helmut' ; 
                    allocation '2b14d02c-2123-484c-84aa-d4a05c25fef5' : ComponentFunctionalAllocation
                        allocate function ::> 'CDT_System Project'::'CDT_System'::'Logical Architecture'::'Logical Functions'::'Root Logical Function'.'Trainer Recieves Concussion Alert'
                        to component ::> 'CDT_System Project'::'CDT_System'::'Logical Architecture'::'Structure'::'Trainer';
                    perform 'CDT_System Project'::'CDT_System'::'Logical Architecture'::'Logical Functions'::'Root Logical Function'.'Trainer Recieves Concussion Alert' ; 
                    allocation '55ff3e59-6377-49cb-8480-821e7bd072f7' : ComponentFunctionalAllocation
                        allocate function ::> 'CDT_System Project'::'CDT_System'::'Logical Architecture'::'Logical Functions'::'Root Logical Function'.'Data can be reviewed'
                        to component ::> 'CDT_System Project'::'CDT_System'::'Logical Architecture'::'Structure'::'Trainer';
                    perform 'CDT_System Project'::'CDT_System'::'Logical Architecture'::'Logical Functions'::'Root Logical Function'.'Data can be reviewed' ; 
                    allocation '547a9180-2281-4706-af3b-7a5c41f68a67' : ComponentFunctionalAllocation
                        allocate function ::> 'CDT_System Project'::'CDT_System'::'Logical Architecture'::'Logical Functions'::'Root Logical Function'.'Executes Policies'
                        to component ::> 'CDT_System Project'::'CDT_System'::'Logical Architecture'::'Structure'::'Trainer';
                    perform 'CDT_System Project'::'CDT_System'::'Logical Architecture'::'Logical Functions'::'Root Logical Function'.'Executes Policies' ; 
                    port 'CP 1' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation '52b0ff1b-2dde-4da5-b94b-eb3d6361682c' : PortAllocation
                            allocate allocatedPort ::> 'CDT_System Project'::'CDT_System'::'Logical Architecture'::'Logical Functions'::'Root Logical Function'.'Data can be reviewed'.'inStored Data '
                            to allocatingPort ::> 'CDT_System Project'::'CDT_System'::'Logical Architecture'::'Structure'::'Trainer'.'CP 1'; 
                        ref allocation '94f059c4-3679-482a-b069-741632a66ca3' : PortAllocation
                            allocate allocatedPort ::> 'CDT_System Project'::'CDT_System'::'Logical Architecture'::'Logical Functions'::'Root Logical Function'.'Recieve Enabled Signal from Athelete Helmut'.'inEnable Signal'
                            to allocatingPort ::> 'CDT_System Project'::'CDT_System'::'Logical Architecture'::'Structure'::'Trainer'.'CP 1'; 
                        ref allocation '6a87d63c-2c94-472c-afdd-c43c17c75a2a' : PortAllocation
                            allocate allocatedPort ::> 'CDT_System Project'::'CDT_System'::'Logical Architecture'::'Logical Functions'::'Root Logical Function'.'Create Unique IDs'.'outID'
                            to allocatingPort ::> 'CDT_System Project'::'CDT_System'::'Logical Architecture'::'Structure'::'Trainer'.'CP 1'; 
                        ref allocation '95b95b62-7993-4751-a964-d89f0dc2a63f' : PortAllocation
                            allocate allocatedPort ::> 'CDT_System Project'::'CDT_System'::'Logical Architecture'::'Logical Functions'::'Root Logical Function'.'Trainer Recieves Concussion Alert'.'inConcussion Alert to Trainer'
                            to allocatingPort ::> 'CDT_System Project'::'CDT_System'::'Logical Architecture'::'Structure'::'Trainer'.'CP 1'; 
                        ref allocation '21a17415-90ce-4c43-be7a-6736eb01aa76' : PortAllocation
                            allocate allocatedPort ::> 'CDT_System Project'::'CDT_System'::'Logical Architecture'::'Logical Functions'::'Root Logical Function'.'Create profiles for Athletes'.'outAthlete Profile'
                            to allocatingPort ::> 'CDT_System Project'::'CDT_System'::'Logical Architecture'::'Structure'::'Trainer'.'CP 1'; 
                        ref allocation 'c640d438-9b92-480b-a8b6-ae401d55f3c5' : PortAllocation
                            allocate allocatedPort ::> 'CDT_System Project'::'CDT_System'::'Logical Architecture'::'Logical Functions'::'Root Logical Function'.'Trainer Recieves Concussion Alert'.'FOP 2'
                            to allocatingPort ::> 'CDT_System Project'::'CDT_System'::'Logical Architecture'::'Structure'::'Trainer'.'CP 1'; 
                        ref allocation '606331d3-cae7-4d07-ae03-8a66cecb3dc9' : PortAllocation
                            allocate allocatedPort ::> 'CDT_System Project'::'CDT_System'::'Logical Architecture'::'Logical Functions'::'Root Logical Function'.'Executes Policies'.'outExecute Policy'
                            to allocatingPort ::> 'CDT_System Project'::'CDT_System'::'Logical Architecture'::'Structure'::'Trainer'.'CP 1'; 
                        ref :>> providedInterfaces =  ('CDT_System Project'::'CDT_System'::'Logical Architecture'::'Interfaces'::'CDT App - T'); 
                        ref :>> ownedPortAllocations =  ('CDT_System Project'::'CDT_System'::'Logical Architecture'::'Structure'::'Trainer'.'CP 1'.'52b0ff1b-2dde-4da5-b94b-eb3d6361682c',
                        'CDT_System Project'::'CDT_System'::'Logical Architecture'::'Structure'::'Trainer'.'CP 1'.'94f059c4-3679-482a-b069-741632a66ca3',
                        'CDT_System Project'::'CDT_System'::'Logical Architecture'::'Structure'::'Trainer'.'CP 1'.'6a87d63c-2c94-472c-afdd-c43c17c75a2a',
                        'CDT_System Project'::'CDT_System'::'Logical Architecture'::'Structure'::'Trainer'.'CP 1'.'95b95b62-7993-4751-a964-d89f0dc2a63f',
                        'CDT_System Project'::'CDT_System'::'Logical Architecture'::'Structure'::'Trainer'.'CP 1'.'21a17415-90ce-4c43-be7a-6736eb01aa76',
                        'CDT_System Project'::'CDT_System'::'Logical Architecture'::'Structure'::'Trainer'.'CP 1'.'c640d438-9b92-480b-a8b6-ae401d55f3c5',
                        'CDT_System Project'::'CDT_System'::'Logical Architecture'::'Structure'::'Trainer'.'CP 1'.'606331d3-cae7-4d07-ae03-8a66cecb3dc9'); 
                        ref :>> requiredInterfaces =  ('CDT_System Project'::'CDT_System'::'Logical Architecture'::'Interfaces'::'CDT App - T'); 
                    }  
                    ref :>> ownedFunctionalAllocation =  ('CDT_System Project'::'CDT_System'::'Logical Architecture'::'Structure'::'Trainer'.'0dcfab07-febd-4a99-aafb-ee9e52837803',
                    'CDT_System Project'::'CDT_System'::'Logical Architecture'::'Structure'::'Trainer'.'d68208c0-4e6f-477d-b830-8393f9adbc71',
                    'CDT_System Project'::'CDT_System'::'Logical Architecture'::'Structure'::'Trainer'.'6bed8a2d-e5e1-46f5-8a49-9859f2a4d36a',
                    'CDT_System Project'::'CDT_System'::'Logical Architecture'::'Structure'::'Trainer'.'d0732047-b6f2-4f18-921b-257dcd71210f',
                    'CDT_System Project'::'CDT_System'::'Logical Architecture'::'Structure'::'Trainer'.'e160c59f-38b8-4cb2-b9f0-b9089bb6ec28',
                    'CDT_System Project'::'CDT_System'::'Logical Architecture'::'Structure'::'Trainer'.'b360201e-a359-4f59-a537-7d90dcca838c',
                    'CDT_System Project'::'CDT_System'::'Logical Architecture'::'Structure'::'Trainer'.'2b14d02c-2123-484c-84aa-d4a05c25fef5',
                    'CDT_System Project'::'CDT_System'::'Logical Architecture'::'Structure'::'Trainer'.'55ff3e59-6377-49cb-8480-821e7bd072f7',
                    'CDT_System Project'::'CDT_System'::'Logical Architecture'::'Structure'::'Trainer'.'547a9180-2281-4706-af3b-7a5c41f68a67'); 
                     
                     
                }  
                part 'Athlete' : LogicalComponent { 
                    attribute :>> isAbstract = false; 
                    attribute :>> isActor = true; 
                    attribute :>> isHuman = false; 
                    allocation '999175cd-ee3c-41e0-bb24-9015e804f06b' : ComponentFunctionalAllocation
                        allocate function ::> 'CDT_System Project'::'CDT_System'::'Logical Architecture'::'Logical Functions'::'Root Logical Function'.'Provide Data for Profile'
                        to component ::> 'CDT_System Project'::'CDT_System'::'Logical Architecture'::'Structure'::'Athlete';
                    perform 'CDT_System Project'::'CDT_System'::'Logical Architecture'::'Logical Functions'::'Root Logical Function'.'Provide Data for Profile' ; 
                    allocation '7ffb011e-8283-40b4-8ad6-fbffbdb917a7' : ComponentFunctionalAllocation
                        allocate function ::> 'CDT_System Project'::'CDT_System'::'Logical Architecture'::'Logical Functions'::'Root Logical Function'.'Recieve ID'
                        to component ::> 'CDT_System Project'::'CDT_System'::'Logical Architecture'::'Structure'::'Athlete';
                    perform 'CDT_System Project'::'CDT_System'::'Logical Architecture'::'Logical Functions'::'Root Logical Function'.'Recieve ID' ; 
                    allocation '6165091f-52da-4b5d-a05b-db2c0fb2ae61' : ComponentFunctionalAllocation
                        allocate function ::> 'CDT_System Project'::'CDT_System'::'Logical Architecture'::'Logical Functions'::'Root Logical Function'.'Insert ID into Sensing Device'
                        to component ::> 'CDT_System Project'::'CDT_System'::'Logical Architecture'::'Structure'::'Athlete';
                    perform 'CDT_System Project'::'CDT_System'::'Logical Architecture'::'Logical Functions'::'Root Logical Function'.'Insert ID into Sensing Device' ; 
                    allocation '53bca230-1e12-4080-a712-58ccc66e547c' : ComponentFunctionalAllocation
                        allocate function ::> 'CDT_System Project'::'CDT_System'::'Logical Architecture'::'Logical Functions'::'Root Logical Function'.'Place on Helmut'
                        to component ::> 'CDT_System Project'::'CDT_System'::'Logical Architecture'::'Structure'::'Athlete';
                    perform 'CDT_System Project'::'CDT_System'::'Logical Architecture'::'Logical Functions'::'Root Logical Function'.'Place on Helmut' ; 
                    allocation 'e93a5d39-fb24-4440-8c32-cabb04ec1f66' : ComponentFunctionalAllocation
                        allocate function ::> 'CDT_System Project'::'CDT_System'::'Logical Architecture'::'Logical Functions'::'Root Logical Function'.'Athlete Particpates in Activity'
                        to component ::> 'CDT_System Project'::'CDT_System'::'Logical Architecture'::'Structure'::'Athlete';
                    perform 'CDT_System Project'::'CDT_System'::'Logical Architecture'::'Logical Functions'::'Root Logical Function'.'Athlete Particpates in Activity' ; 
                    allocation '34e4d5d8-299b-433f-b3ca-73c914ffa6d1' : ComponentFunctionalAllocation
                        allocate function ::> 'CDT_System Project'::'CDT_System'::'Logical Architecture'::'Logical Functions'::'Root Logical Function'.'Yield to Evaluation'
                        to component ::> 'CDT_System Project'::'CDT_System'::'Logical Architecture'::'Structure'::'Athlete';
                    perform 'CDT_System Project'::'CDT_System'::'Logical Architecture'::'Logical Functions'::'Root Logical Function'.'Yield to Evaluation' ; 
                    allocation '0595080e-ba51-408b-8ad3-136af10ae81f' : ComponentFunctionalAllocation
                        allocate function ::> 'CDT_System Project'::'CDT_System'::'Logical Architecture'::'Logical Functions'::'Root Logical Function'.'Report Received'
                        to component ::> 'CDT_System Project'::'CDT_System'::'Logical Architecture'::'Structure'::'Athlete';
                    perform 'CDT_System Project'::'CDT_System'::'Logical Architecture'::'Logical Functions'::'Root Logical Function'.'Report Received' ; 
                    port 'CP 1' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::OUT; 
                        attribute :>> isUnique = false; 
                        attribute :>> isReadOnly = false; 
                        attribute :>> isMinInclusive = false; 
                        attribute :>> isStatic = false; 
                        attribute :>> isOrdered = false; 
                        attribute :>> isAbstract = false; 
                        ref allocation '592ec738-359a-4694-8247-5dac3bea11f2' : PortAllocation
                            allocate allocatedPort ::> 'CDT_System Project'::'CDT_System'::'Logical Architecture'::'Logical Functions'::'Root Logical Function'.'Athlete Particpates in Activity'.'outActivity'
                            to allocatingPort ::> 'CDT_System Project'::'CDT_System'::'Logical Architecture'::'Structure'::'Athlete'.'CP 1'; 
                        ref allocation 'fe5da3ec-25ae-4bf6-ad16-725855c27d18' : PortAllocation
                            allocate allocatedPort ::> 'CDT_System Project'::'CDT_System'::'Logical Architecture'::'Logical Functions'::'Root Logical Function'.'Place on Helmut'.'outHead '
                            to allocatingPort ::> 'CDT_System Project'::'CDT_System'::'Logical Architecture'::'Structure'::'Athlete'.'CP 1'; 
                        ref :>> ownedPortAllocations =  ('CDT_System Project'::'CDT_System'::'Logical Architecture'::'Structure'::'Athlete'.'CP 1'.'592ec738-359a-4694-8247-5dac3bea11f2',
                        'CDT_System Project'::'CDT_System'::'Logical Architecture'::'Structure'::'Athlete'.'CP 1'.'fe5da3ec-25ae-4bf6-ad16-725855c27d18'); 
                        ref :>> requiredInterfaces =  ('CDT_System Project'::'CDT_System'::'Logical Architecture'::'Interfaces'::'Athlete to Helmut'); 
                    }  
                    port 'CP 2' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation '0556536c-f419-445e-bba1-875b60e6727f' : PortAllocation
                            allocate allocatedPort ::> 'CDT_System Project'::'CDT_System'::'Logical Architecture'::'Logical Functions'::'Root Logical Function'.'Report Received'.'inAthlete Report'
                            to allocatingPort ::> 'CDT_System Project'::'CDT_System'::'Logical Architecture'::'Structure'::'Athlete'.'CP 2'; 
                        ref :>> providedInterfaces =  ('CDT_System Project'::'CDT_System'::'Logical Architecture'::'Interfaces'::'SA- Athlete'); 
                        ref :>> ownedPortAllocations =  ('CDT_System Project'::'CDT_System'::'Logical Architecture'::'Structure'::'Athlete'.'CP 2'.'0556536c-f419-445e-bba1-875b60e6727f'); 
                    }  
                    ref :>> ownedFunctionalAllocation =  ('CDT_System Project'::'CDT_System'::'Logical Architecture'::'Structure'::'Athlete'.'999175cd-ee3c-41e0-bb24-9015e804f06b',
                    'CDT_System Project'::'CDT_System'::'Logical Architecture'::'Structure'::'Athlete'.'7ffb011e-8283-40b4-8ad6-fbffbdb917a7',
                    'CDT_System Project'::'CDT_System'::'Logical Architecture'::'Structure'::'Athlete'.'6165091f-52da-4b5d-a05b-db2c0fb2ae61',
                    'CDT_System Project'::'CDT_System'::'Logical Architecture'::'Structure'::'Athlete'.'53bca230-1e12-4080-a712-58ccc66e547c',
                    'CDT_System Project'::'CDT_System'::'Logical Architecture'::'Structure'::'Athlete'.'e93a5d39-fb24-4440-8c32-cabb04ec1f66',
                    'CDT_System Project'::'CDT_System'::'Logical Architecture'::'Structure'::'Athlete'.'34e4d5d8-299b-433f-b3ca-73c914ffa6d1',
                    'CDT_System Project'::'CDT_System'::'Logical Architecture'::'Structure'::'Athlete'.'0595080e-ba51-408b-8ad3-136af10ae81f'); 
                     
                     
                }  
                part 'Instituion' : LogicalComponent { 
                    attribute :>> isAbstract = false; 
                    attribute :>> isActor = true; 
                    attribute :>> isHuman = false; 
                    allocation '227d6f93-b522-45a1-a634-e2f1da9d5dde' : ComponentFunctionalAllocation
                        allocate function ::> 'CDT_System Project'::'CDT_System'::'Logical Architecture'::'Logical Functions'::'Root Logical Function'.'Aquire System'
                        to component ::> 'CDT_System Project'::'CDT_System'::'Logical Architecture'::'Structure'::'Instituion';
                    perform 'CDT_System Project'::'CDT_System'::'Logical Architecture'::'Logical Functions'::'Root Logical Function'.'Aquire System' ; 
                    allocation '481bb541-9cca-4705-8af1-9b761cbe8a5d' : ComponentFunctionalAllocation
                        allocate function ::> 'CDT_System Project'::'CDT_System'::'Logical Architecture'::'Logical Functions'::'Root Logical Function'.'Report Received'
                        to component ::> 'CDT_System Project'::'CDT_System'::'Logical Architecture'::'Structure'::'Instituion';
                    perform 'CDT_System Project'::'CDT_System'::'Logical Architecture'::'Logical Functions'::'Root Logical Function'.'Report Received' ; 
                    allocation 'e1583470-30a0-4a05-8925-5ddc508981c3' : ComponentFunctionalAllocation
                        allocate function ::> 'CDT_System Project'::'CDT_System'::'Logical Architecture'::'Logical Functions'::'Root Logical Function'.'Established Concussion Policy'
                        to component ::> 'CDT_System Project'::'CDT_System'::'Logical Architecture'::'Structure'::'Instituion';
                    perform 'CDT_System Project'::'CDT_System'::'Logical Architecture'::'Logical Functions'::'Root Logical Function'.'Established Concussion Policy' ; 
                    port 'CP 1' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation '699654bb-5882-48d1-9467-c7b57d778c73' : PortAllocation
                            allocate allocatedPort ::> 'CDT_System Project'::'CDT_System'::'Logical Architecture'::'Logical Functions'::'Root Logical Function'.'Report Received'.'inInstition Report'
                            to allocatingPort ::> 'CDT_System Project'::'CDT_System'::'Logical Architecture'::'Structure'::'Instituion'.'CP 1'; 
                        ref :>> providedInterfaces =  ('CDT_System Project'::'CDT_System'::'Logical Architecture'::'Interfaces'::'SA-Inst'); 
                        ref :>> ownedPortAllocations =  ('CDT_System Project'::'CDT_System'::'Logical Architecture'::'Structure'::'Instituion'.'CP 1'.'699654bb-5882-48d1-9467-c7b57d778c73'); 
                    }  
                    ref :>> ownedFunctionalAllocation =  ('CDT_System Project'::'CDT_System'::'Logical Architecture'::'Structure'::'Instituion'.'227d6f93-b522-45a1-a634-e2f1da9d5dde',
                    'CDT_System Project'::'CDT_System'::'Logical Architecture'::'Structure'::'Instituion'.'481bb541-9cca-4705-8af1-9b761cbe8a5d',
                    'CDT_System Project'::'CDT_System'::'Logical Architecture'::'Structure'::'Instituion'.'e1583470-30a0-4a05-8925-5ddc508981c3'); 
                     
                     
                }  
                part 'Parent' : LogicalComponent { 
                    attribute :>> isAbstract = false; 
                    attribute :>> isActor = true; 
                    attribute :>> isHuman = false; 
                    allocation 'd5a68885-5aec-4d46-9b4b-2808c5080884' : ComponentFunctionalAllocation
                        allocate function ::> 'CDT_System Project'::'CDT_System'::'Logical Architecture'::'Logical Functions'::'Root Logical Function'.'Report received'
                        to component ::> 'CDT_System Project'::'CDT_System'::'Logical Architecture'::'Structure'::'Parent';
                    perform 'CDT_System Project'::'CDT_System'::'Logical Architecture'::'Logical Functions'::'Root Logical Function'.'Report received' ; 
                    port 'CP 1' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation '8c56de80-833c-4f86-b053-3dbbbafb3548' : PortAllocation
                            allocate allocatedPort ::> 'CDT_System Project'::'CDT_System'::'Logical Architecture'::'Logical Functions'::'Root Logical Function'.'Report received'.'inParen Report'
                            to allocatingPort ::> 'CDT_System Project'::'CDT_System'::'Logical Architecture'::'Structure'::'Parent'.'CP 1'; 
                        ref :>> providedInterfaces =  ('CDT_System Project'::'CDT_System'::'Logical Architecture'::'Interfaces'::'SA-Parent'); 
                        ref :>> ownedPortAllocations =  ('CDT_System Project'::'CDT_System'::'Logical Architecture'::'Structure'::'Parent'.'CP 1'.'8c56de80-833c-4f86-b053-3dbbbafb3548'); 
                    }  
                    ref :>> ownedFunctionalAllocation =  ('CDT_System Project'::'CDT_System'::'Logical Architecture'::'Structure'::'Parent'.'d5a68885-5aec-4d46-9b4b-2808c5080884'); 
                     
                     
                }  
                interface '2bf42ea5-c76a-4de2-8609-15fda7c207f0' : ComponentExchange 
                    connect source ::> 'CDT_System Project'::'CDT_System'::'Logical Architecture'::'Structure'::'Athlete'.'CP 1'
                    to  target ::> 'CDT_System Project'::'CDT_System'::'Logical Architecture'::'Structure'::'CDT System'.'Helmet Receives a Hit'.'CP 1' { 
                    attribute :>> isOriented = false; 
                    attribute :>> interfaceName = "Athlete to Helmut"; 
                    attribute :>> kind = ComponentExchangeKind::FLOW; 
                    allocation '72611cf8-e71b-4189-8f8b-dcf972aa61e7' : ComponentExchangeFunctionalExchangeAllocation
                        allocate functionalExchange ::> 'CDT_System Project'::'CDT_System'::'Logical Architecture'::'Logical Functions'::'Root Logical Function'.'033e3152-51b3-45d7-a9a1-aae2f3decad1'
                        to componentExchange ::> 'CDT_System Project'::'CDT_System'::'Logical Architecture'::'Structure'::'2bf42ea5-c76a-4de2-8609-15fda7c207f0'; 
                    allocation '7e83001f-f556-4012-ac46-36a0fcea4476' : ComponentExchangeFunctionalExchangeAllocation
                        allocate functionalExchange ::> 'CDT_System Project'::'CDT_System'::'Logical Architecture'::'Logical Functions'::'Root Logical Function'.'4e51009a-8ee1-4cd3-87bb-2a6ea590ffad'
                        to componentExchange ::> 'CDT_System Project'::'CDT_System'::'Logical Architecture'::'Structure'::'2bf42ea5-c76a-4de2-8609-15fda7c207f0'; 
                    ref :>> ownedComponentExchangeFunctionalExchangeAllocations =  ('CDT_System Project'::'CDT_System'::'Logical Architecture'::'Structure'::'2bf42ea5-c76a-4de2-8609-15fda7c207f0'.'72611cf8-e71b-4189-8f8b-dcf972aa61e7',
                    'CDT_System Project'::'CDT_System'::'Logical Architecture'::'Structure'::'2bf42ea5-c76a-4de2-8609-15fda7c207f0'.'7e83001f-f556-4012-ac46-36a0fcea4476'); 
                }  
                interface '7d672e9f-af27-418b-aa8b-9d7e409b3b8b' : ComponentExchange 
                    connect source ::> 'CDT_System Project'::'CDT_System'::'Logical Architecture'::'Structure'::'CDT System'.'CDT App'.'CP 2'
                    to  target ::> 'CDT_System Project'::'CDT_System'::'Logical Architecture'::'Structure'::'Trainer'.'CP 1' { 
                    attribute :>> isOriented = false; 
                    attribute :>> interfaceName = "CDT App - T"; 
                    attribute :>> kind = ComponentExchangeKind::FLOW; 
                    allocation '7c250463-bdf9-4a48-930d-8c7d949b55bd' : ComponentExchangeFunctionalExchangeAllocation
                        allocate functionalExchange ::> 'CDT_System Project'::'CDT_System'::'Logical Architecture'::'Logical Functions'::'Root Logical Function'.'01f8b08a-4640-420b-8d83-dba3864e5805'
                        to componentExchange ::> 'CDT_System Project'::'CDT_System'::'Logical Architecture'::'Structure'::'7d672e9f-af27-418b-aa8b-9d7e409b3b8b'; 
                    allocation 'a33530dd-5f15-406b-a3a5-24ebcd26fd7a' : ComponentExchangeFunctionalExchangeAllocation
                        allocate functionalExchange ::> 'CDT_System Project'::'CDT_System'::'Logical Architecture'::'Logical Functions'::'Root Logical Function'.'1006a2a3-51b8-4014-b186-94587fe4de06'
                        to componentExchange ::> 'CDT_System Project'::'CDT_System'::'Logical Architecture'::'Structure'::'7d672e9f-af27-418b-aa8b-9d7e409b3b8b'; 
                    allocation '7f07d2e2-2d43-49d9-8227-b763d22d91ad' : ComponentExchangeFunctionalExchangeAllocation
                        allocate functionalExchange ::> 'CDT_System Project'::'CDT_System'::'Logical Architecture'::'Logical Functions'::'Root Logical Function'.'de2a11d8-2409-417a-8eab-929d60e962a8'
                        to componentExchange ::> 'CDT_System Project'::'CDT_System'::'Logical Architecture'::'Structure'::'7d672e9f-af27-418b-aa8b-9d7e409b3b8b'; 
                    allocation 'bca257dd-ce45-4f93-a04f-affa8ad2c659' : ComponentExchangeFunctionalExchangeAllocation
                        allocate functionalExchange ::> 'CDT_System Project'::'CDT_System'::'Logical Architecture'::'Logical Functions'::'Root Logical Function'.'aa8aeda1-33ce-4fc7-be1b-a304cb2015fe'
                        to componentExchange ::> 'CDT_System Project'::'CDT_System'::'Logical Architecture'::'Structure'::'7d672e9f-af27-418b-aa8b-9d7e409b3b8b'; 
                    allocation 'd529adf8-e676-4d5d-afd8-04fc1f654c1e' : ComponentExchangeFunctionalExchangeAllocation
                        allocate functionalExchange ::> 'CDT_System Project'::'CDT_System'::'Logical Architecture'::'Logical Functions'::'Root Logical Function'.'16ac8629-9665-4574-a074-9098e8fa193c'
                        to componentExchange ::> 'CDT_System Project'::'CDT_System'::'Logical Architecture'::'Structure'::'7d672e9f-af27-418b-aa8b-9d7e409b3b8b'; 
                    allocation '7970b509-3ff9-4a73-8540-f542c7d345d2' : ComponentExchangeFunctionalExchangeAllocation
                        allocate functionalExchange ::> 'CDT_System Project'::'CDT_System'::'Logical Architecture'::'Logical Functions'::'Root Logical Function'.'141f7a3c-ac31-4dcb-97f0-030743f4cf14'
                        to componentExchange ::> 'CDT_System Project'::'CDT_System'::'Logical Architecture'::'Structure'::'7d672e9f-af27-418b-aa8b-9d7e409b3b8b'; 
                    allocation '2f89fc41-9fa0-49fb-910e-f26ec39b9a12' : ComponentExchangeFunctionalExchangeAllocation
                        allocate functionalExchange ::> 'CDT_System Project'::'CDT_System'::'Logical Architecture'::'Logical Functions'::'Root Logical Function'.'4776ac92-de15-48ad-a25f-efac32182fe7'
                        to componentExchange ::> 'CDT_System Project'::'CDT_System'::'Logical Architecture'::'Structure'::'7d672e9f-af27-418b-aa8b-9d7e409b3b8b'; 
                    ref :>> ownedComponentExchangeFunctionalExchangeAllocations =  ('CDT_System Project'::'CDT_System'::'Logical Architecture'::'Structure'::'7d672e9f-af27-418b-aa8b-9d7e409b3b8b'.'7c250463-bdf9-4a48-930d-8c7d949b55bd',
                    'CDT_System Project'::'CDT_System'::'Logical Architecture'::'Structure'::'7d672e9f-af27-418b-aa8b-9d7e409b3b8b'.'a33530dd-5f15-406b-a3a5-24ebcd26fd7a',
                    'CDT_System Project'::'CDT_System'::'Logical Architecture'::'Structure'::'7d672e9f-af27-418b-aa8b-9d7e409b3b8b'.'7f07d2e2-2d43-49d9-8227-b763d22d91ad',
                    'CDT_System Project'::'CDT_System'::'Logical Architecture'::'Structure'::'7d672e9f-af27-418b-aa8b-9d7e409b3b8b'.'bca257dd-ce45-4f93-a04f-affa8ad2c659',
                    'CDT_System Project'::'CDT_System'::'Logical Architecture'::'Structure'::'7d672e9f-af27-418b-aa8b-9d7e409b3b8b'.'d529adf8-e676-4d5d-afd8-04fc1f654c1e',
                    'CDT_System Project'::'CDT_System'::'Logical Architecture'::'Structure'::'7d672e9f-af27-418b-aa8b-9d7e409b3b8b'.'7970b509-3ff9-4a73-8540-f542c7d345d2',
                    'CDT_System Project'::'CDT_System'::'Logical Architecture'::'Structure'::'7d672e9f-af27-418b-aa8b-9d7e409b3b8b'.'2f89fc41-9fa0-49fb-910e-f26ec39b9a12'); 
                }  
                interface 'bc51e7d9-32bf-446d-b3ad-1c2d4b1639bb' : ComponentExchange 
                    connect source ::> 'CDT_System Project'::'CDT_System'::'Logical Architecture'::'Structure'::'CDT System'.'Secure Application'.'CP 3'
                    to  target ::> 'CDT_System Project'::'CDT_System'::'Logical Architecture'::'Structure'::'Athlete'.'CP 2' { 
                    attribute :>> isOriented = false; 
                    attribute :>> interfaceName = "SA- Athlete"; 
                    attribute :>> kind = ComponentExchangeKind::FLOW; 
                    allocation '8efecb46-e1ee-406a-ab54-ea051526ad51' : ComponentExchangeFunctionalExchangeAllocation
                        allocate functionalExchange ::> 'CDT_System Project'::'CDT_System'::'Logical Architecture'::'Logical Functions'::'Root Logical Function'.'635ccece-c152-41cc-995f-6716650aa8fa'
                        to componentExchange ::> 'CDT_System Project'::'CDT_System'::'Logical Architecture'::'Structure'::'bc51e7d9-32bf-446d-b3ad-1c2d4b1639bb'; 
                    ref :>> ownedComponentExchangeFunctionalExchangeAllocations =  ('CDT_System Project'::'CDT_System'::'Logical Architecture'::'Structure'::'bc51e7d9-32bf-446d-b3ad-1c2d4b1639bb'.'8efecb46-e1ee-406a-ab54-ea051526ad51'); 
                }  
                interface '53b0ef6c-77ea-412f-81d9-37b883982b8a' : ComponentExchange 
                    connect source ::> 'CDT_System Project'::'CDT_System'::'Logical Architecture'::'Structure'::'CDT System'.'Secure Application'.'CP 4'
                    to  target ::> 'CDT_System Project'::'CDT_System'::'Logical Architecture'::'Structure'::'Instituion'.'CP 1' { 
                    attribute :>> isOriented = false; 
                    attribute :>> interfaceName = "SA-Inst"; 
                    attribute :>> kind = ComponentExchangeKind::FLOW; 
                    allocation '98796c5d-65d3-4d8f-874d-feacfb1e0403' : ComponentExchangeFunctionalExchangeAllocation
                        allocate functionalExchange ::> 'CDT_System Project'::'CDT_System'::'Logical Architecture'::'Logical Functions'::'Root Logical Function'.'7c65fcce-2e69-4088-8879-09f2ae47a639'
                        to componentExchange ::> 'CDT_System Project'::'CDT_System'::'Logical Architecture'::'Structure'::'53b0ef6c-77ea-412f-81d9-37b883982b8a'; 
                    ref :>> ownedComponentExchangeFunctionalExchangeAllocations =  ('CDT_System Project'::'CDT_System'::'Logical Architecture'::'Structure'::'53b0ef6c-77ea-412f-81d9-37b883982b8a'.'98796c5d-65d3-4d8f-874d-feacfb1e0403'); 
                }  
                interface '6357bdb2-8fed-403e-8b71-ad2254876136' : ComponentExchange 
                    connect source ::> 'CDT_System Project'::'CDT_System'::'Logical Architecture'::'Structure'::'CDT System'.'Secure Application'.'CP 5'
                    to  target ::> 'CDT_System Project'::'CDT_System'::'Logical Architecture'::'Structure'::'Parent'.'CP 1' { 
                    attribute :>> isOriented = false; 
                    attribute :>> interfaceName = "SA-Parent"; 
                    attribute :>> kind = ComponentExchangeKind::FLOW; 
                    allocation 'df2411dc-ff18-4bdd-a199-651d6b9c1e9c' : ComponentExchangeFunctionalExchangeAllocation
                        allocate functionalExchange ::> 'CDT_System Project'::'CDT_System'::'Logical Architecture'::'Logical Functions'::'Root Logical Function'.'38922abf-b0ac-4ded-8226-7b753f82ecd3'
                        to componentExchange ::> 'CDT_System Project'::'CDT_System'::'Logical Architecture'::'Structure'::'6357bdb2-8fed-403e-8b71-ad2254876136'; 
                    ref :>> ownedComponentExchangeFunctionalExchangeAllocations =  ('CDT_System Project'::'CDT_System'::'Logical Architecture'::'Structure'::'6357bdb2-8fed-403e-8b71-ad2254876136'.'df2411dc-ff18-4bdd-a199-651d6b9c1e9c'); 
                }  
            } 
            package  'Logical Functions' {
                @PackageMeta {
                    type = "LogicalFunctionPkg";
                } 
                action 'Root Logical Function' : LogicalFunction  { 
                    attribute :>> isDerived = false; 
                    attribute :>> aggregationKind = AggregationKind::UNSET; 
                    attribute :>> isFinal = false; 
                    attribute :>> isPartOfKey = false; 
                    attribute :>> kind = FunctionKind::FUNCTION; 
                    attribute :>> isMaxInclusive = false; 
                    attribute :>> isUnique = false; 
                    attribute :>> isReadOnly = false; 
                    attribute :>> isMinInclusive = false; 
                    attribute :>> isStatic = false; 
                    attribute :>> isOrdered = false; 
                    attribute :>> isAbstract = false; 
                    action 'Acquire Device' : FunctionalChain  { 
                        attribute :>> kind = FunctionalChainKind::SIMPLE; 
                        connection '8cb16e57-a3da-4546-8ba3-8c0dc4157ad9' : FunctionalChainInvolvementLink 
                            connect source ::> 'CDT_System Project'::'CDT_System'::'Logical Architecture'::'Logical Functions'::'Root Logical Function'.'Acquire Device'.'8f506208-5b81-45d0-bce0-86bc4eb629c3'
                            to  target ::> 'CDT_System Project'::'CDT_System'::'Logical Architecture'::'Logical Functions'::'Root Logical Function'.'Acquire Device'.'00bfaa2b-e8ee-4d9c-b239-82196761ad3f' {

                                ref :>> involved = 'CDT_System Project'::'CDT_System'::'Logical Architecture'::'Logical Functions'::'Root Logical Function'.'36a2318b-871f-4e1b-8559-d5343e010562';

                            } 
                        ref action '00bfaa2b-e8ee-4d9c-b239-82196761ad3f' = 'CDT_System Project'::'CDT_System'::'Logical Architecture'::'Logical Functions'::'Root Logical Function'.'Create profiles for Athletes'; 
                        ref action '8f506208-5b81-45d0-bce0-86bc4eb629c3' = 'CDT_System Project'::'CDT_System'::'Logical Architecture'::'Logical Functions'::'Root Logical Function'.'Provide Data for Profile'; 
                        connection '0b6a9710-39a2-48c5-8ea0-37ff48e771f8' : FunctionalChainInvolvementLink 
                            connect source ::> 'CDT_System Project'::'CDT_System'::'Logical Architecture'::'Logical Functions'::'Root Logical Function'.'Acquire Device'.'7bbe1e87-7db1-4ec2-921f-9f00a4d3aa3b'
                            to  target ::> 'CDT_System Project'::'CDT_System'::'Logical Architecture'::'Logical Functions'::'Root Logical Function'.'Acquire Device'.'00bfaa2b-e8ee-4d9c-b239-82196761ad3f' {

                                ref :>> involved = 'CDT_System Project'::'CDT_System'::'Logical Architecture'::'Logical Functions'::'Root Logical Function'.'08b345f8-96d0-4939-879f-5725053e5a0d';

                            } 
                        ref action '7bbe1e87-7db1-4ec2-921f-9f00a4d3aa3b' = 'CDT_System Project'::'CDT_System'::'Logical Architecture'::'Logical Functions'::'Root Logical Function'.'Aquire System'; 
                        connection 'f0ecc40f-c1da-4b12-ac34-0ebdfbc8b28f' : FunctionalChainInvolvementLink 
                            connect source ::> 'CDT_System Project'::'CDT_System'::'Logical Architecture'::'Logical Functions'::'Root Logical Function'.'Acquire Device'.'00bfaa2b-e8ee-4d9c-b239-82196761ad3f'
                            to  target ::> 'CDT_System Project'::'CDT_System'::'Logical Architecture'::'Logical Functions'::'Root Logical Function'.'Acquire Device'.'9b93b1b0-dc58-421a-af3a-4a40e11c0d30' {

                                ref :>> involved = 'CDT_System Project'::'CDT_System'::'Logical Architecture'::'Logical Functions'::'Root Logical Function'.'16ac8629-9665-4574-a074-9098e8fa193c';

                            } 
                        ref action '59d52608-91f2-4293-aeb1-df4303d1c8da' = 'CDT_System Project'::'CDT_System'::'Logical Architecture'::'Logical Functions'::'Root Logical Function'.'Create Unique IDs'; 
                        connection '072b5e09-4f55-4f93-9b79-a1a60a551304' : FunctionalChainInvolvementLink 
                            connect source ::> 'CDT_System Project'::'CDT_System'::'Logical Architecture'::'Logical Functions'::'Root Logical Function'.'Acquire Device'.'00bfaa2b-e8ee-4d9c-b239-82196761ad3f'
                            to  target ::> 'CDT_System Project'::'CDT_System'::'Logical Architecture'::'Logical Functions'::'Root Logical Function'.'Acquire Device'.'59d52608-91f2-4293-aeb1-df4303d1c8da' {

                                ref :>> involved = 'CDT_System Project'::'CDT_System'::'Logical Architecture'::'Logical Functions'::'Root Logical Function'.'34b74dfd-243a-40cc-a6a4-658f76ffe895';

                            } 
                        connection '5402610e-74bc-42b5-b763-43b4f783a0ca' : FunctionalChainInvolvementLink 
                            connect source ::> 'CDT_System Project'::'CDT_System'::'Logical Architecture'::'Logical Functions'::'Root Logical Function'.'Acquire Device'.'59d52608-91f2-4293-aeb1-df4303d1c8da'
                            to  target ::> 'CDT_System Project'::'CDT_System'::'Logical Architecture'::'Logical Functions'::'Root Logical Function'.'Acquire Device'.'61c3d957-7f90-4815-b424-82a5b1e65b25' {

                                ref :>> involved = 'CDT_System Project'::'CDT_System'::'Logical Architecture'::'Logical Functions'::'Root Logical Function'.'de2a11d8-2409-417a-8eab-929d60e962a8';

                            } 
                        ref action 'ac1476c2-8d35-42b3-8593-0220819b92ee' = 'CDT_System Project'::'CDT_System'::'Logical Architecture'::'Logical Functions'::'Root Logical Function'.'Provide ID to Athlete'; 
                        connection '926ae2f1-c7a7-483c-80c2-d267d4377e7a' : FunctionalChainInvolvementLink 
                            connect source ::> 'CDT_System Project'::'CDT_System'::'Logical Architecture'::'Logical Functions'::'Root Logical Function'.'Acquire Device'.'03fb80a5-100e-4bae-ae84-79822e5f9535'
                            to  target ::> 'CDT_System Project'::'CDT_System'::'Logical Architecture'::'Logical Functions'::'Root Logical Function'.'Acquire Device'.'ac1476c2-8d35-42b3-8593-0220819b92ee' {

                                ref :>> involved = 'CDT_System Project'::'CDT_System'::'Logical Architecture'::'Logical Functions'::'Root Logical Function'.'aafcfdab-163f-41ca-8526-0c45de5d6af2';

                            } 
                        ref action '12d6520a-e4ee-4226-8ffc-1e3386088ba4' = 'CDT_System Project'::'CDT_System'::'Logical Architecture'::'Logical Functions'::'Root Logical Function'.'Recieve ID'; 
                        connection 'b0add469-c2ac-4e0d-8363-ce6a32ad494e' : FunctionalChainInvolvementLink 
                            connect source ::> 'CDT_System Project'::'CDT_System'::'Logical Architecture'::'Logical Functions'::'Root Logical Function'.'Acquire Device'.'ac1476c2-8d35-42b3-8593-0220819b92ee'
                            to  target ::> 'CDT_System Project'::'CDT_System'::'Logical Architecture'::'Logical Functions'::'Root Logical Function'.'Acquire Device'.'12d6520a-e4ee-4226-8ffc-1e3386088ba4' {

                                ref :>> involved = 'CDT_System Project'::'CDT_System'::'Logical Architecture'::'Logical Functions'::'Root Logical Function'.'6f427cb0-5e63-42c7-9a23-b81b452b3e1d';

                            } 
                        ref action '9b93b1b0-dc58-421a-af3a-4a40e11c0d30' = 'CDT_System Project'::'CDT_System'::'Logical Architecture'::'Logical Functions'::'Root Logical Function'.'Store Profile'.'Gather Profile Data'; 
                        ref action '61c3d957-7f90-4815-b424-82a5b1e65b25' = 'CDT_System Project'::'CDT_System'::'Logical Architecture'::'Logical Functions'::'Root Logical Function'.'Create Unique IDs for Athlete'.'Initiate ID Creation'; 
                        ref action '03fb80a5-100e-4bae-ae84-79822e5f9535' = 'CDT_System Project'::'CDT_System'::'Logical Architecture'::'Logical Functions'::'Root Logical Function'.'Create Unique IDs for Athlete'.'Create and Program ID'; 
                        ref action 'cd2dea10-5895-4016-9863-d0758b8b5a5a' = 'CDT_System Project'::'CDT_System'::'Logical Architecture'::'Logical Functions'::'Root Logical Function'.'Create Unique IDs for Athlete'.'Create ID'; 
                        connection '42ab97ca-a681-4d77-9c38-4b75daffd83a' : FunctionalChainInvolvementLink 
                            connect source ::> 'CDT_System Project'::'CDT_System'::'Logical Architecture'::'Logical Functions'::'Root Logical Function'.'Acquire Device'.'61c3d957-7f90-4815-b424-82a5b1e65b25'
                            to  target ::> 'CDT_System Project'::'CDT_System'::'Logical Architecture'::'Logical Functions'::'Root Logical Function'.'Acquire Device'.'cd2dea10-5895-4016-9863-d0758b8b5a5a' {

                                ref :>> involved = 'CDT_System Project'::'CDT_System'::'Logical Architecture'::'Logical Functions'::'Root Logical Function'.'Create Unique IDs for Athlete'.'5c40769b-d826-496b-894d-6efeb8a0a5b5';

                            } 
                        connection 'cbbc0f05-639e-4177-b307-4364914c0684' : FunctionalChainInvolvementLink 
                            connect source ::> 'CDT_System Project'::'CDT_System'::'Logical Architecture'::'Logical Functions'::'Root Logical Function'.'Acquire Device'.'cd2dea10-5895-4016-9863-d0758b8b5a5a'
                            to  target ::> 'CDT_System Project'::'CDT_System'::'Logical Architecture'::'Logical Functions'::'Root Logical Function'.'Acquire Device'.'03fb80a5-100e-4bae-ae84-79822e5f9535' {

                                ref :>> involved = 'CDT_System Project'::'CDT_System'::'Logical Architecture'::'Logical Functions'::'Root Logical Function'.'Create Unique IDs for Athlete'.'1974be04-a3fa-41df-b9e5-06ce4a06cb99';

                            } 
                        ref action 'c18d5b26-b30e-4d33-9b52-2ddf32b4e73b' = 'CDT_System Project'::'CDT_System'::'Logical Architecture'::'Logical Functions'::'Root Logical Function'.'Store Profile'.'Store Profile'; 
                        connection '2b7bac17-77c8-4f68-8768-2e4aa6b843af' : FunctionalChainInvolvementLink 
                            connect source ::> 'CDT_System Project'::'CDT_System'::'Logical Architecture'::'Logical Functions'::'Root Logical Function'.'Acquire Device'.'9b93b1b0-dc58-421a-af3a-4a40e11c0d30'
                            to  target ::> 'CDT_System Project'::'CDT_System'::'Logical Architecture'::'Logical Functions'::'Root Logical Function'.'Acquire Device'.'c18d5b26-b30e-4d33-9b52-2ddf32b4e73b' {

                                ref :>> involved = 'CDT_System Project'::'CDT_System'::'Logical Architecture'::'Logical Functions'::'Root Logical Function'.'Store Profile'.'4614f066-5aa3-4b81-a308-99d5a57d3889';

                            } 
                        connection '1fb88c43-2441-423e-9bd2-e926bf1fc31e' : FunctionalChainInvolvementLink 
                            connect source ::> 'CDT_System Project'::'CDT_System'::'Logical Architecture'::'Logical Functions'::'Root Logical Function'.'Acquire Device'.'c18d5b26-b30e-4d33-9b52-2ddf32b4e73b'
                            to  target ::> 'CDT_System Project'::'CDT_System'::'Logical Architecture'::'Logical Functions'::'Root Logical Function'.'Acquire Device'.'cd2dea10-5895-4016-9863-d0758b8b5a5a' {

                                ref :>> involved = 'CDT_System Project'::'CDT_System'::'Logical Architecture'::'Logical Functions'::'Root Logical Function'.'2da9d91f-1db5-4020-a709-32ac5622aa79';

                            } 
                         
                    }  
                    action 'Maintain' : FunctionalChain  { 
                        attribute :>> kind = FunctionalChainKind::SIMPLE; 
                        connection '1f3d0789-9b36-42c1-a7ca-fe55d9e699a5' : FunctionalChainInvolvementLink 
                            connect source ::> 'CDT_System Project'::'CDT_System'::'Logical Architecture'::'Logical Functions'::'Root Logical Function'.'Maintain'.'e82dc609-076e-4fb7-8c67-74f72655bf8a'
                            to  target ::> 'CDT_System Project'::'CDT_System'::'Logical Architecture'::'Logical Functions'::'Root Logical Function'.'Maintain'.'2a9e3a9f-7356-438d-820f-5fc8ac9c04be' {

                                ref :>> involved = 'CDT_System Project'::'CDT_System'::'Logical Architecture'::'Logical Functions'::'Root Logical Function'.'0bb64163-5187-4559-aa62-9bccb4369cfe';

                            } 
                        ref action '2a9e3a9f-7356-438d-820f-5fc8ac9c04be' = 'CDT_System Project'::'CDT_System'::'Logical Architecture'::'Logical Functions'::'Root Logical Function'.'Assemble System Components'; 
                        ref action 'e82dc609-076e-4fb7-8c67-74f72655bf8a' = 'CDT_System Project'::'CDT_System'::'Logical Architecture'::'Logical Functions'::'Root Logical Function'.'Aquire System'; 
                        connection '619f97c6-1bc0-4ae3-a986-922322b9d638' : FunctionalChainInvolvementLink 
                            connect source ::> 'CDT_System Project'::'CDT_System'::'Logical Architecture'::'Logical Functions'::'Root Logical Function'.'Maintain'.'3de3f54b-0703-4bf4-a528-c31f586bf8b8'
                            to  target ::> 'CDT_System Project'::'CDT_System'::'Logical Architecture'::'Logical Functions'::'Root Logical Function'.'Maintain'.'2a9e3a9f-7356-438d-820f-5fc8ac9c04be' {

                                ref :>> involved = 'CDT_System Project'::'CDT_System'::'Logical Architecture'::'Logical Functions'::'Root Logical Function'.'e9d82fae-346e-4c0b-9a92-dcc49d7a2bbb';

                            } 
                        ref action '3de3f54b-0703-4bf4-a528-c31f586bf8b8' = 'CDT_System Project'::'CDT_System'::'Logical Architecture'::'Logical Functions'::'Root Logical Function'.'Provide access to helmut mounting'; 
                        connection '34f81318-c897-41cd-b721-3e610a2fe826' : FunctionalChainInvolvementLink 
                            connect source ::> 'CDT_System Project'::'CDT_System'::'Logical Architecture'::'Logical Functions'::'Root Logical Function'.'Maintain'.'55124b8d-cbab-43a5-b852-0ee5992577a2'
                            to  target ::> 'CDT_System Project'::'CDT_System'::'Logical Architecture'::'Logical Functions'::'Root Logical Function'.'Maintain'.'2a9e3a9f-7356-438d-820f-5fc8ac9c04be' {

                                ref :>> involved = 'CDT_System Project'::'CDT_System'::'Logical Architecture'::'Logical Functions'::'Root Logical Function'.'55e3ecb0-03f8-41d9-a02c-abb32c6cfe0c';

                            } 
                        ref action '55124b8d-cbab-43a5-b852-0ee5992577a2' = 'CDT_System Project'::'CDT_System'::'Logical Architecture'::'Logical Functions'::'Root Logical Function'.'Provide access to sensing device mounting'; 
                        connection 'b6a443a5-e909-4b49-bc57-68a11e9d14ca' : FunctionalChainInvolvementLink 
                            connect source ::> 'CDT_System Project'::'CDT_System'::'Logical Architecture'::'Logical Functions'::'Root Logical Function'.'Maintain'.'2a9e3a9f-7356-438d-820f-5fc8ac9c04be'
                            to  target ::> 'CDT_System Project'::'CDT_System'::'Logical Architecture'::'Logical Functions'::'Root Logical Function'.'Maintain'.'45bb6e30-b4e0-4bd7-a315-7cfb77a7c9cc' {

                                ref :>> involved = 'CDT_System Project'::'CDT_System'::'Logical Architecture'::'Logical Functions'::'Root Logical Function'.'813cc0b2-5aca-4246-a3d7-66055075ecd6';

                            } 
                        ref action '45bb6e30-b4e0-4bd7-a315-7cfb77a7c9cc' = 'CDT_System Project'::'CDT_System'::'Logical Architecture'::'Logical Functions'::'Root Logical Function'.'Prep the device for use'; 
                         
                    }  
                    action 'Activate Detection Device' : FunctionalChain  { 
                        attribute :>> kind = FunctionalChainKind::SIMPLE; 
                        connection '14c489c8-417c-4b40-b41c-9f47a4900368' : FunctionalChainInvolvementLink 
                            connect source ::> 'CDT_System Project'::'CDT_System'::'Logical Architecture'::'Logical Functions'::'Root Logical Function'.'Activate Detection Device'.'ef9638be-d4ec-449b-9cc4-3af202d12c1d'
                            to  target ::> 'CDT_System Project'::'CDT_System'::'Logical Architecture'::'Logical Functions'::'Root Logical Function'.'Activate Detection Device'.'40606333-6732-4aa9-93bb-59da23ec82fa' {

                                ref :>> involved = 'CDT_System Project'::'CDT_System'::'Logical Architecture'::'Logical Functions'::'Root Logical Function'.'b8bd28fc-460e-46d1-a8a0-3cbe9832ab95';

                            } 
                        ref action '40606333-6732-4aa9-93bb-59da23ec82fa' = 'CDT_System Project'::'CDT_System'::'Logical Architecture'::'Logical Functions'::'Root Logical Function'.'Insert ID into Sensing Device'; 
                        ref action 'ef9638be-d4ec-449b-9cc4-3af202d12c1d' = 'CDT_System Project'::'CDT_System'::'Logical Architecture'::'Logical Functions'::'Root Logical Function'.'Recieve ID'; 
                        connection '9fc7c5a0-8a9f-4938-a4ed-36a617c868bf' : FunctionalChainInvolvementLink 
                            connect source ::> 'CDT_System Project'::'CDT_System'::'Logical Architecture'::'Logical Functions'::'Root Logical Function'.'Activate Detection Device'.'40606333-6732-4aa9-93bb-59da23ec82fa'
                            to  target ::> 'CDT_System Project'::'CDT_System'::'Logical Architecture'::'Logical Functions'::'Root Logical Function'.'Activate Detection Device'.'32e9d05c-928c-4337-88ae-456cc0cff3c8' {

                                ref :>> involved = 'CDT_System Project'::'CDT_System'::'Logical Architecture'::'Logical Functions'::'Root Logical Function'.'00d758e5-8a75-4f64-b22e-78cc1cadaeb8';

                            } 
                        ref action '32e9d05c-928c-4337-88ae-456cc0cff3c8' = 'CDT_System Project'::'CDT_System'::'Logical Architecture'::'Logical Functions'::'Root Logical Function'.'Recieve ID'; 
                        connection '18d8674a-e30a-4000-bdd5-29f15c164e9c' : FunctionalChainInvolvementLink 
                            connect source ::> 'CDT_System Project'::'CDT_System'::'Logical Architecture'::'Logical Functions'::'Root Logical Function'.'Activate Detection Device'.'40606333-6732-4aa9-93bb-59da23ec82fa'
                            to  target ::> 'CDT_System Project'::'CDT_System'::'Logical Architecture'::'Logical Functions'::'Root Logical Function'.'Activate Detection Device'.'89ec13f2-246f-4f2d-8554-64b02cd2bcc3' {

                                ref :>> involved = 'CDT_System Project'::'CDT_System'::'Logical Architecture'::'Logical Functions'::'Root Logical Function'.'ca27fda2-31e3-46f1-8961-666dd0d43912';

                            } 
                        ref action '89ec13f2-246f-4f2d-8554-64b02cd2bcc3' = 'CDT_System Project'::'CDT_System'::'Logical Architecture'::'Logical Functions'::'Root Logical Function'.'Place on Helmut'; 
                        connection '68164aab-6a0d-4e7f-a6f1-1e155c2f8b02' : FunctionalChainInvolvementLink 
                            connect source ::> 'CDT_System Project'::'CDT_System'::'Logical Architecture'::'Logical Functions'::'Root Logical Function'.'Activate Detection Device'.'32e9d05c-928c-4337-88ae-456cc0cff3c8'
                            to  target ::> 'CDT_System Project'::'CDT_System'::'Logical Architecture'::'Logical Functions'::'Root Logical Function'.'Activate Detection Device'.'e9875736-86c6-4dfa-aa5a-2136fa349555' {

                                ref :>> involved = 'CDT_System Project'::'CDT_System'::'Logical Architecture'::'Logical Functions'::'Root Logical Function'.'b4eab17b-ed8d-4af7-869d-998f966d1bc2';

                            } 
                        ref action 'e9875736-86c6-4dfa-aa5a-2136fa349555' = 'CDT_System Project'::'CDT_System'::'Logical Architecture'::'Logical Functions'::'Root Logical Function'.'Enable Secure Collection'; 
                        connection '0d783ef5-8e80-4c1e-91e6-48abe15af3ff' : FunctionalChainInvolvementLink 
                            connect source ::> 'CDT_System Project'::'CDT_System'::'Logical Architecture'::'Logical Functions'::'Root Logical Function'.'Activate Detection Device'.'e9875736-86c6-4dfa-aa5a-2136fa349555'
                            to  target ::> 'CDT_System Project'::'CDT_System'::'Logical Architecture'::'Logical Functions'::'Root Logical Function'.'Activate Detection Device'.'3d14f16f-eaa5-49b6-9144-f37aaa7c8d4c' {

                                ref :>> involved = 'CDT_System Project'::'CDT_System'::'Logical Architecture'::'Logical Functions'::'Root Logical Function'.'de8f7c10-fd24-4d5f-ad53-43652989cb4c';

                            } 
                        connection 'd8dc0242-e327-47fc-bd30-bfcb3696da10' : FunctionalChainInvolvementLink 
                            connect source ::> 'CDT_System Project'::'CDT_System'::'Logical Architecture'::'Logical Functions'::'Root Logical Function'.'Activate Detection Device'.'89ec13f2-246f-4f2d-8554-64b02cd2bcc3'
                            to  target ::> 'CDT_System Project'::'CDT_System'::'Logical Architecture'::'Logical Functions'::'Root Logical Function'.'Activate Detection Device'.'97da7c03-121a-4a69-b393-337afbe3e967' {

                                ref :>> involved = 'CDT_System Project'::'CDT_System'::'Logical Architecture'::'Logical Functions'::'Root Logical Function'.'4e51009a-8ee1-4cd3-87bb-2a6ea590ffad';

                            } 
                        ref action '97da7c03-121a-4a69-b393-337afbe3e967' = 'CDT_System Project'::'CDT_System'::'Logical Architecture'::'Logical Functions'::'Root Logical Function'.'Receive Athlete '; 
                        connection '7878c768-8253-444f-a60a-40a7f6f62087' : FunctionalChainInvolvementLink 
                            connect source ::> 'CDT_System Project'::'CDT_System'::'Logical Architecture'::'Logical Functions'::'Root Logical Function'.'Activate Detection Device'.'97da7c03-121a-4a69-b393-337afbe3e967'
                            to  target ::> 'CDT_System Project'::'CDT_System'::'Logical Architecture'::'Logical Functions'::'Root Logical Function'.'Activate Detection Device'.'3d14f16f-eaa5-49b6-9144-f37aaa7c8d4c' {

                                ref :>> involved = 'CDT_System Project'::'CDT_System'::'Logical Architecture'::'Logical Functions'::'Root Logical Function'.'56e3f648-295a-488f-b3d0-b6c6fd35f619';

                            } 
                        ref action 'f5293da7-e19e-46ba-acc3-a5c12b953924' = 'CDT_System Project'::'CDT_System'::'Logical Architecture'::'Logical Functions'::'Root Logical Function'.'Provide ID Information'; 
                        connection 'b7c52780-f015-4d2c-bdc9-d355a967bdc5' : FunctionalChainInvolvementLink 
                            connect source ::> 'CDT_System Project'::'CDT_System'::'Logical Architecture'::'Logical Functions'::'Root Logical Function'.'Activate Detection Device'.'f5293da7-e19e-46ba-acc3-a5c12b953924'
                            to  target ::> 'CDT_System Project'::'CDT_System'::'Logical Architecture'::'Logical Functions'::'Root Logical Function'.'Activate Detection Device'.'e9875736-86c6-4dfa-aa5a-2136fa349555' {

                                ref :>> involved = 'CDT_System Project'::'CDT_System'::'Logical Architecture'::'Logical Functions'::'Root Logical Function'.'dbbb6ead-6656-4c2d-b504-bbe6fc344884';

                            } 
                        ref action 'fab3ae0b-6de3-4515-9338-0cee0998416e' = 'CDT_System Project'::'CDT_System'::'Logical Architecture'::'Logical Functions'::'Root Logical Function'.'Recieve Enabled Signal from Athelete Helmut'; 
                        connection '32492ee5-9900-44fe-92e4-6f89974a8a65' : FunctionalChainInvolvementLink 
                            connect source ::> 'CDT_System Project'::'CDT_System'::'Logical Architecture'::'Logical Functions'::'Root Logical Function'.'Activate Detection Device'.'68f7b4e3-91d7-4bdc-b2c7-a104c310a243'
                            to  target ::> 'CDT_System Project'::'CDT_System'::'Logical Architecture'::'Logical Functions'::'Root Logical Function'.'Activate Detection Device'.'fab3ae0b-6de3-4515-9338-0cee0998416e' {

                                ref :>> involved = 'CDT_System Project'::'CDT_System'::'Logical Architecture'::'Logical Functions'::'Root Logical Function'.'1006a2a3-51b8-4014-b186-94587fe4de06';

                            } 
                        ref action '3d14f16f-eaa5-49b6-9144-f37aaa7c8d4c' = 'CDT_System Project'::'CDT_System'::'Logical Architecture'::'Logical Functions'::'Root Logical Function'.'Enable Monitoring'.'Enable Monitoring'; 
                        ref action '68f7b4e3-91d7-4bdc-b2c7-a104c310a243' = 'CDT_System Project'::'CDT_System'::'Logical Architecture'::'Logical Functions'::'Root Logical Function'.'Enable Monitoring'.'Enable Indicated'; 
                        ref action '397a4356-4bea-4c68-8fb0-954888ee632e' = 'CDT_System Project'::'CDT_System'::'Logical Architecture'::'Logical Functions'::'Root Logical Function'.'Enable Monitoring'.'Relay Enabled Message'; 
                        connection 'd09ee2b7-99ce-4c50-8c04-88eaaa71da4e' : FunctionalChainInvolvementLink 
                            connect source ::> 'CDT_System Project'::'CDT_System'::'Logical Architecture'::'Logical Functions'::'Root Logical Function'.'Activate Detection Device'.'3d14f16f-eaa5-49b6-9144-f37aaa7c8d4c'
                            to  target ::> 'CDT_System Project'::'CDT_System'::'Logical Architecture'::'Logical Functions'::'Root Logical Function'.'Activate Detection Device'.'397a4356-4bea-4c68-8fb0-954888ee632e' {

                                ref :>> involved = 'CDT_System Project'::'CDT_System'::'Logical Architecture'::'Logical Functions'::'Root Logical Function'.'Enable Monitoring'.'ed518be9-43ff-4d81-b589-3a8c39857811';

                            } 
                        ref action '8618bea8-4055-4f05-b0bd-d6b71994e2fd' = 'CDT_System Project'::'CDT_System'::'Logical Architecture'::'Logical Functions'::'Root Logical Function'.'Enable Monitoring'.'Look for bluetooth connect'; 
                        connection 'f6007ef3-98e3-4d39-b1f1-a9d514db684a' : FunctionalChainInvolvementLink 
                            connect source ::> 'CDT_System Project'::'CDT_System'::'Logical Architecture'::'Logical Functions'::'Root Logical Function'.'Activate Detection Device'.'3d14f16f-eaa5-49b6-9144-f37aaa7c8d4c'
                            to  target ::> 'CDT_System Project'::'CDT_System'::'Logical Architecture'::'Logical Functions'::'Root Logical Function'.'Activate Detection Device'.'8618bea8-4055-4f05-b0bd-d6b71994e2fd' {

                                ref :>> involved = 'CDT_System Project'::'CDT_System'::'Logical Architecture'::'Logical Functions'::'Root Logical Function'.'Enable Monitoring'.'c0f41030-26d8-4248-b51e-cc0d0bd5ba25';

                            } 
                        ref action '3358270d-aadd-4945-a27c-03cf8ebb07fe' = 'CDT_System Project'::'CDT_System'::'Logical Architecture'::'Logical Functions'::'Root Logical Function'.'Enable Monitoring'.'Enable Recored'; 
                        connection '1022f275-ddb2-4699-b621-ff9734a9c679' : FunctionalChainInvolvementLink 
                            connect source ::> 'CDT_System Project'::'CDT_System'::'Logical Architecture'::'Logical Functions'::'Root Logical Function'.'Activate Detection Device'.'397a4356-4bea-4c68-8fb0-954888ee632e'
                            to  target ::> 'CDT_System Project'::'CDT_System'::'Logical Architecture'::'Logical Functions'::'Root Logical Function'.'Activate Detection Device'.'3358270d-aadd-4945-a27c-03cf8ebb07fe' {

                                ref :>> involved = 'CDT_System Project'::'CDT_System'::'Logical Architecture'::'Logical Functions'::'Root Logical Function'.'Enable Monitoring'.'346ba0de-117f-4838-bd24-1b822d200e79';

                            } 
                        connection '34c1eb4d-cb10-468d-85ae-63106aba7925' : FunctionalChainInvolvementLink 
                            connect source ::> 'CDT_System Project'::'CDT_System'::'Logical Architecture'::'Logical Functions'::'Root Logical Function'.'Activate Detection Device'.'3358270d-aadd-4945-a27c-03cf8ebb07fe'
                            to  target ::> 'CDT_System Project'::'CDT_System'::'Logical Architecture'::'Logical Functions'::'Root Logical Function'.'Activate Detection Device'.'68f7b4e3-91d7-4bdc-b2c7-a104c310a243' {

                                ref :>> involved = 'CDT_System Project'::'CDT_System'::'Logical Architecture'::'Logical Functions'::'Root Logical Function'.'Enable Monitoring'.'6bc089b3-336d-4890-a903-ab77f625b6e0';

                            } 
                        ref action '3ce303c2-fc75-42fe-a5f5-4d39b2656634' = 'CDT_System Project'::'CDT_System'::'Logical Architecture'::'Logical Functions'::'Root Logical Function'.'Enable Monitoring'.'Enable Bluetoth Connect'; 
                        connection 'd29eee5d-e9fc-4cbf-90cb-940bbcce6796' : FunctionalChainInvolvementLink 
                            connect source ::> 'CDT_System Project'::'CDT_System'::'Logical Architecture'::'Logical Functions'::'Root Logical Function'.'Activate Detection Device'.'68f7b4e3-91d7-4bdc-b2c7-a104c310a243'
                            to  target ::> 'CDT_System Project'::'CDT_System'::'Logical Architecture'::'Logical Functions'::'Root Logical Function'.'Activate Detection Device'.'3ce303c2-fc75-42fe-a5f5-4d39b2656634' {

                                ref :>> involved = 'CDT_System Project'::'CDT_System'::'Logical Architecture'::'Logical Functions'::'Root Logical Function'.'Enable Monitoring'.'2c13b94c-54bc-4937-b982-6e5870f616af';

                            } 
                        connection '4703853f-fd51-4a6d-b8f3-d8573db43efa' : FunctionalChainInvolvementLink 
                            connect source ::> 'CDT_System Project'::'CDT_System'::'Logical Architecture'::'Logical Functions'::'Root Logical Function'.'Activate Detection Device'.'3ce303c2-fc75-42fe-a5f5-4d39b2656634'
                            to  target ::> 'CDT_System Project'::'CDT_System'::'Logical Architecture'::'Logical Functions'::'Root Logical Function'.'Activate Detection Device'.'8618bea8-4055-4f05-b0bd-d6b71994e2fd' {

                                ref :>> involved = 'CDT_System Project'::'CDT_System'::'Logical Architecture'::'Logical Functions'::'Root Logical Function'.'Enable Monitoring'.'dab7038c-c1c1-441a-ac01-772653b7c3a4';

                            } 
                         
                    }  
                    action 'Download Data' : FunctionalChain  { 
                        attribute :>> kind = FunctionalChainKind::SIMPLE; 
                        connection '0db40dcd-2ae3-4197-aeec-b7131685e4aa' : FunctionalChainInvolvementLink 
                            connect source ::> 'CDT_System Project'::'CDT_System'::'Logical Architecture'::'Logical Functions'::'Root Logical Function'.'Download Data'.'14303800-5ae9-4a81-b137-1f3fecb95bbf'
                            to  target ::> 'CDT_System Project'::'CDT_System'::'Logical Architecture'::'Logical Functions'::'Root Logical Function'.'Download Data'.'bdab222b-9b31-4774-8d03-c7ab58b0dd42' {

                                ref :>> involved = 'CDT_System Project'::'CDT_System'::'Logical Architecture'::'Logical Functions'::'Root Logical Function'.'614f2cf6-af23-4751-b457-0ab203481315';

                            } 
                        ref action 'bdab222b-9b31-4774-8d03-c7ab58b0dd42' = 'CDT_System Project'::'CDT_System'::'Logical Architecture'::'Logical Functions'::'Root Logical Function'.'Yield to Evaluation'; 
                        ref action '14303800-5ae9-4a81-b137-1f3fecb95bbf' = 'CDT_System Project'::'CDT_System'::'Logical Architecture'::'Logical Functions'::'Root Logical Function'.'Trainer Recieves Concussion Alert'; 
                        connection '32942d58-9ace-49a2-8197-ad78b57e8910' : FunctionalChainInvolvementLink 
                            connect source ::> 'CDT_System Project'::'CDT_System'::'Logical Architecture'::'Logical Functions'::'Root Logical Function'.'Download Data'.'bdab222b-9b31-4774-8d03-c7ab58b0dd42'
                            to  target ::> 'CDT_System Project'::'CDT_System'::'Logical Architecture'::'Logical Functions'::'Root Logical Function'.'Download Data'.'2c1dc913-4281-4d84-9069-bef4ca6cd3af' {

                                ref :>> involved = 'CDT_System Project'::'CDT_System'::'Logical Architecture'::'Logical Functions'::'Root Logical Function'.'2e9251b0-4ed5-4638-ac5f-70e316e6fd80';

                            } 
                        connection '8e4a1706-838f-45b2-ac69-478e8ebf813a' : FunctionalChainInvolvementLink 
                            connect source ::> 'CDT_System Project'::'CDT_System'::'Logical Architecture'::'Logical Functions'::'Root Logical Function'.'Download Data'.'2c1dc913-4281-4d84-9069-bef4ca6cd3af'
                            to  target ::> 'CDT_System Project'::'CDT_System'::'Logical Architecture'::'Logical Functions'::'Root Logical Function'.'Download Data'.'d82ac76d-3232-4b71-a104-1364d17cd215' {

                                ref :>> involved = 'CDT_System Project'::'CDT_System'::'Logical Architecture'::'Logical Functions'::'Root Logical Function'.'71992433-b730-4c78-b2c6-634c4f622ff2';

                            } 
                        connection '2df0a86b-b582-4e2c-8cf9-65c4bd171107' : FunctionalChainInvolvementLink 
                            connect source ::> 'CDT_System Project'::'CDT_System'::'Logical Architecture'::'Logical Functions'::'Root Logical Function'.'Download Data'.'56e878d7-582b-41b9-a005-080faac463eb'
                            to  target ::> 'CDT_System Project'::'CDT_System'::'Logical Architecture'::'Logical Functions'::'Root Logical Function'.'Download Data'.'315bd06f-9baa-4f35-b0a7-d02d6608d315' {

                                ref :>> involved = 'CDT_System Project'::'CDT_System'::'Logical Architecture'::'Logical Functions'::'Root Logical Function'.'01f8b08a-4640-420b-8d83-dba3864e5805';

                            } 
                        ref action '315bd06f-9baa-4f35-b0a7-d02d6608d315' = 'CDT_System Project'::'CDT_System'::'Logical Architecture'::'Logical Functions'::'Root Logical Function'.'Data can be reviewed'; 
                        connection '2abf5742-e969-40c4-b2cc-234b683b5051' : FunctionalChainInvolvementLink 
                            connect source ::> 'CDT_System Project'::'CDT_System'::'Logical Architecture'::'Logical Functions'::'Root Logical Function'.'Download Data'.'315bd06f-9baa-4f35-b0a7-d02d6608d315'
                            to  target ::> 'CDT_System Project'::'CDT_System'::'Logical Architecture'::'Logical Functions'::'Root Logical Function'.'Download Data'.'abf93fad-50f8-4535-acd3-abbe38a0165f' {

                                ref :>> involved = 'CDT_System Project'::'CDT_System'::'Logical Architecture'::'Logical Functions'::'Root Logical Function'.'2f84f25a-c0c3-4273-bddd-f328cfa6ebd4';

                            } 
                        ref action 'abf93fad-50f8-4535-acd3-abbe38a0165f' = 'CDT_System Project'::'CDT_System'::'Logical Architecture'::'Logical Functions'::'Root Logical Function'.'Executes Policies'; 
                        connection '8d42142e-d751-4dce-a76b-1c8e5252b957' : FunctionalChainInvolvementLink 
                            connect source ::> 'CDT_System Project'::'CDT_System'::'Logical Architecture'::'Logical Functions'::'Root Logical Function'.'Download Data'.'abf93fad-50f8-4535-acd3-abbe38a0165f'
                            to  target ::> 'CDT_System Project'::'CDT_System'::'Logical Architecture'::'Logical Functions'::'Root Logical Function'.'Download Data'.'c02edaa5-5274-41ac-a94e-eba6ab7d9960' {

                                ref :>> involved = 'CDT_System Project'::'CDT_System'::'Logical Architecture'::'Logical Functions'::'Root Logical Function'.'4776ac92-de15-48ad-a25f-efac32182fe7';

                            } 
                        connection 'b66063a7-ca10-4638-ac93-fdd19b932fad' : FunctionalChainInvolvementLink 
                            connect source ::> 'CDT_System Project'::'CDT_System'::'Logical Architecture'::'Logical Functions'::'Root Logical Function'.'Download Data'.'d1ce1672-203d-49a6-9b15-404568b41ec3'
                            to  target ::> 'CDT_System Project'::'CDT_System'::'Logical Architecture'::'Logical Functions'::'Root Logical Function'.'Download Data'.'d244e5e5-acdb-4b4b-83c9-139b9f8d41b1' {

                                ref :>> involved = 'CDT_System Project'::'CDT_System'::'Logical Architecture'::'Logical Functions'::'Root Logical Function'.'635ccece-c152-41cc-995f-6716650aa8fa';

                            } 
                        ref action 'd244e5e5-acdb-4b4b-83c9-139b9f8d41b1' = 'CDT_System Project'::'CDT_System'::'Logical Architecture'::'Logical Functions'::'Root Logical Function'.'Report Received'; 
                        connection '186476ea-f855-4491-bc1a-8b41c13f9ecb' : FunctionalChainInvolvementLink 
                            connect source ::> 'CDT_System Project'::'CDT_System'::'Logical Architecture'::'Logical Functions'::'Root Logical Function'.'Download Data'.'d1ce1672-203d-49a6-9b15-404568b41ec3'
                            to  target ::> 'CDT_System Project'::'CDT_System'::'Logical Architecture'::'Logical Functions'::'Root Logical Function'.'Download Data'.'cfca5412-2228-4e25-9903-840fc5e9f879' {

                                ref :>> involved = 'CDT_System Project'::'CDT_System'::'Logical Architecture'::'Logical Functions'::'Root Logical Function'.'7c65fcce-2e69-4088-8879-09f2ae47a639';

                            } 
                        ref action 'cfca5412-2228-4e25-9903-840fc5e9f879' = 'CDT_System Project'::'CDT_System'::'Logical Architecture'::'Logical Functions'::'Root Logical Function'.'Report Received'; 
                        connection 'c93ebd71-9d6d-42c5-bb00-edc823f6c4a6' : FunctionalChainInvolvementLink 
                            connect source ::> 'CDT_System Project'::'CDT_System'::'Logical Architecture'::'Logical Functions'::'Root Logical Function'.'Download Data'.'d1ce1672-203d-49a6-9b15-404568b41ec3'
                            to  target ::> 'CDT_System Project'::'CDT_System'::'Logical Architecture'::'Logical Functions'::'Root Logical Function'.'Download Data'.'9e53828f-0bb0-41b1-ae12-0b30548d3684' {

                                ref :>> involved = 'CDT_System Project'::'CDT_System'::'Logical Architecture'::'Logical Functions'::'Root Logical Function'.'38922abf-b0ac-4ded-8226-7b753f82ecd3';

                            } 
                        ref action '9e53828f-0bb0-41b1-ae12-0b30548d3684' = 'CDT_System Project'::'CDT_System'::'Logical Architecture'::'Logical Functions'::'Root Logical Function'.'Report received'; 
                        ref action '2c1dc913-4281-4d84-9069-bef4ca6cd3af' = 'CDT_System Project'::'CDT_System'::'Logical Architecture'::'Logical Functions'::'Root Logical Function'.'Data is Retrieved'.'Intitate Data Retrieval'; 
                        ref action 'd82ac76d-3232-4b71-a104-1364d17cd215' = 'CDT_System Project'::'CDT_System'::'Logical Architecture'::'Logical Functions'::'Root Logical Function'.'Data stored'.'Data Stored'; 
                        ref action '56e878d7-582b-41b9-a005-080faac463eb' = 'CDT_System Project'::'CDT_System'::'Logical Architecture'::'Logical Functions'::'Root Logical Function'.'Data stored'.'Data is Presented'; 
                        ref action 'c02edaa5-5274-41ac-a94e-eba6ab7d9960' = 'CDT_System Project'::'CDT_System'::'Logical Architecture'::'Logical Functions'::'Root Logical Function'.'Generates Reports'.'Request Report to be sent'; 
                        ref action 'd1ce1672-203d-49a6-9b15-404568b41ec3' = 'CDT_System Project'::'CDT_System'::'Logical Architecture'::'Logical Functions'::'Root Logical Function'.'Generates Reports'.'Generate Reports'; 
                        ref action '49734301-9ab7-4dfc-a391-46bff55f9418' = 'CDT_System Project'::'CDT_System'::'Logical Architecture'::'Logical Functions'::'Root Logical Function'.'Data is Retrieved'.'Request the Data '; 
                        connection '34def441-3965-41b8-92f9-3d60e7a7c9c7' : FunctionalChainInvolvementLink 
                            connect source ::> 'CDT_System Project'::'CDT_System'::'Logical Architecture'::'Logical Functions'::'Root Logical Function'.'Download Data'.'2c1dc913-4281-4d84-9069-bef4ca6cd3af'
                            to  target ::> 'CDT_System Project'::'CDT_System'::'Logical Architecture'::'Logical Functions'::'Root Logical Function'.'Download Data'.'49734301-9ab7-4dfc-a391-46bff55f9418' {

                                ref :>> involved = 'CDT_System Project'::'CDT_System'::'Logical Architecture'::'Logical Functions'::'Root Logical Function'.'Data is Retrieved'.'c667cdb0-6ba8-4c8d-b6aa-52cec107730e';

                            } 
                        ref action '93b7e428-bb06-411e-bd7d-490e8035c731' = 'CDT_System Project'::'CDT_System'::'Logical Architecture'::'Logical Functions'::'Root Logical Function'.'Data is Retrieved'.'Provide Hit Data'; 
                        connection '047b728e-98e4-4762-a859-eb9570973466' : FunctionalChainInvolvementLink 
                            connect source ::> 'CDT_System Project'::'CDT_System'::'Logical Architecture'::'Logical Functions'::'Root Logical Function'.'Download Data'.'49734301-9ab7-4dfc-a391-46bff55f9418'
                            to  target ::> 'CDT_System Project'::'CDT_System'::'Logical Architecture'::'Logical Functions'::'Root Logical Function'.'Download Data'.'93b7e428-bb06-411e-bd7d-490e8035c731' {

                                ref :>> involved = 'CDT_System Project'::'CDT_System'::'Logical Architecture'::'Logical Functions'::'Root Logical Function'.'Data is Retrieved'.'b63a6c42-4adc-4f2d-bbb7-8a230c7a9862';

                            } 
                        connection '428d74d7-78a9-44ad-9856-6c31873e5ab2' : FunctionalChainInvolvementLink 
                            connect source ::> 'CDT_System Project'::'CDT_System'::'Logical Architecture'::'Logical Functions'::'Root Logical Function'.'Download Data'.'d82ac76d-3232-4b71-a104-1364d17cd215'
                            to  target ::> 'CDT_System Project'::'CDT_System'::'Logical Architecture'::'Logical Functions'::'Root Logical Function'.'Download Data'.'56e878d7-582b-41b9-a005-080faac463eb' {

                                ref :>> involved = 'CDT_System Project'::'CDT_System'::'Logical Architecture'::'Logical Functions'::'Root Logical Function'.'Data stored'.'062e99f3-77a8-4aff-8249-e8b8a460a254';

                            } 
                        connection '3b1a4bda-fc15-4630-be07-7edb4ed484ac' : FunctionalChainInvolvementLink 
                            connect source ::> 'CDT_System Project'::'CDT_System'::'Logical Architecture'::'Logical Functions'::'Root Logical Function'.'Download Data'.'c02edaa5-5274-41ac-a94e-eba6ab7d9960'
                            to  target ::> 'CDT_System Project'::'CDT_System'::'Logical Architecture'::'Logical Functions'::'Root Logical Function'.'Download Data'.'d1ce1672-203d-49a6-9b15-404568b41ec3' {

                                ref :>> involved = 'CDT_System Project'::'CDT_System'::'Logical Architecture'::'Logical Functions'::'Root Logical Function'.'Generates Reports'.'a968678a-bdee-4cc3-8a24-1cd23df515a3';

                            } 
                         
                    }  
                    action 'Detect Concussion' : FunctionalChain  { 
                        attribute :>> kind = FunctionalChainKind::SIMPLE; 
                        connection '74560a6c-f959-4724-86e8-59c170bdb04a' : FunctionalChainInvolvementLink 
                            connect source ::> 'CDT_System Project'::'CDT_System'::'Logical Architecture'::'Logical Functions'::'Root Logical Function'.'Detect Concussion'.'9928cfdc-3b6a-46d0-9f2c-362deda26508'
                            to  target ::> 'CDT_System Project'::'CDT_System'::'Logical Architecture'::'Logical Functions'::'Root Logical Function'.'Detect Concussion'.'2a1adc59-3d92-40d4-9522-088da5255100' {

                                ref :>> involved = 'CDT_System Project'::'CDT_System'::'Logical Architecture'::'Logical Functions'::'Root Logical Function'.'033e3152-51b3-45d7-a9a1-aae2f3decad1';

                            } 
                        ref action '2a1adc59-3d92-40d4-9522-088da5255100' = 'CDT_System Project'::'CDT_System'::'Logical Architecture'::'Logical Functions'::'Root Logical Function'.'Helmet Receives a Hit'; 
                        ref action '9928cfdc-3b6a-46d0-9f2c-362deda26508' = 'CDT_System Project'::'CDT_System'::'Logical Architecture'::'Logical Functions'::'Root Logical Function'.'Athlete Particpates in Activity'; 
                        connection 'bb4dda60-5b3b-4ee0-af48-19effb243ec6' : FunctionalChainInvolvementLink 
                            connect source ::> 'CDT_System Project'::'CDT_System'::'Logical Architecture'::'Logical Functions'::'Root Logical Function'.'Detect Concussion'.'2a1adc59-3d92-40d4-9522-088da5255100'
                            to  target ::> 'CDT_System Project'::'CDT_System'::'Logical Architecture'::'Logical Functions'::'Root Logical Function'.'Detect Concussion'.'0b44cc68-134e-49ff-aa39-7c4f993fc68e' {

                                ref :>> involved = 'CDT_System Project'::'CDT_System'::'Logical Architecture'::'Logical Functions'::'Root Logical Function'.'68e7ee56-30a5-4c17-8bfb-5309173b9a78';

                            } 
                        ref action '0b44cc68-134e-49ff-aa39-7c4f993fc68e' = 'CDT_System Project'::'CDT_System'::'Logical Architecture'::'Logical Functions'::'Root Logical Function'.'Device records Hit'; 
                        connection 'a9b5e356-1207-4275-8877-c9a5cdfde31f' : FunctionalChainInvolvementLink 
                            connect source ::> 'CDT_System Project'::'CDT_System'::'Logical Architecture'::'Logical Functions'::'Root Logical Function'.'Detect Concussion'.'0b44cc68-134e-49ff-aa39-7c4f993fc68e'
                            to  target ::> 'CDT_System Project'::'CDT_System'::'Logical Architecture'::'Logical Functions'::'Root Logical Function'.'Detect Concussion'.'8c0ea5ed-d270-4cb8-a6e8-3d53b4c28e83' {

                                ref :>> involved = 'CDT_System Project'::'CDT_System'::'Logical Architecture'::'Logical Functions'::'Root Logical Function'.'97bdedf8-82ae-456e-8aa0-5a2822061c06';

                            } 
                        connection 'b2da0b99-fc1e-46bf-931a-2880e587b5cc' : FunctionalChainInvolvementLink 
                            connect source ::> 'CDT_System Project'::'CDT_System'::'Logical Architecture'::'Logical Functions'::'Root Logical Function'.'Detect Concussion'.'0b44cc68-134e-49ff-aa39-7c4f993fc68e'
                            to  target ::> 'CDT_System Project'::'CDT_System'::'Logical Architecture'::'Logical Functions'::'Root Logical Function'.'Detect Concussion'.'3572c696-a4df-4124-beaf-63cc9451e773' {

                                ref :>> involved = 'CDT_System Project'::'CDT_System'::'Logical Architecture'::'Logical Functions'::'Root Logical Function'.'51513826-9e5b-41a3-8a8a-e83bd29f289a';

                            } 
                        connection '00a8515a-680d-4eab-bc6a-34394a13cf40' : FunctionalChainInvolvementLink 
                            connect source ::> 'CDT_System Project'::'CDT_System'::'Logical Architecture'::'Logical Functions'::'Root Logical Function'.'Detect Concussion'.'d8ca79bf-e32d-43d9-8d31-e70289d1c9a9'
                            to  target ::> 'CDT_System Project'::'CDT_System'::'Logical Architecture'::'Logical Functions'::'Root Logical Function'.'Detect Concussion'.'15642a40-a1ce-40ed-a687-42b10169e280' {

                                ref :>> involved = 'CDT_System Project'::'CDT_System'::'Logical Architecture'::'Logical Functions'::'Root Logical Function'.'aa8aeda1-33ce-4fc7-be1b-a304cb2015fe';

                            } 
                        ref action '15642a40-a1ce-40ed-a687-42b10169e280' = 'CDT_System Project'::'CDT_System'::'Logical Architecture'::'Logical Functions'::'Root Logical Function'.'Trainer Recieves Concussion Alert'; 
                        ref action '8c0ea5ed-d270-4cb8-a6e8-3d53b4c28e83' = 'CDT_System Project'::'CDT_System'::'Logical Architecture'::'Logical Functions'::'Root Logical Function'.'Device alerts possible Concussion'.'Send message'; 
                        ref action 'd8ca79bf-e32d-43d9-8d31-e70289d1c9a9' = 'CDT_System Project'::'CDT_System'::'Logical Architecture'::'Logical Functions'::'Root Logical Function'.'Device alerts possible Concussion'.'Alert the Training'; 
                        ref action 'd2220262-3839-40f3-85b5-2efeb1b2c315' = 'CDT_System Project'::'CDT_System'::'Logical Architecture'::'Logical Functions'::'Root Logical Function'.'Device alerts possible Concussion'.'Relay message'; 
                        connection 'a6b2ee5b-d74c-400b-8d6a-c83694661b9a' : FunctionalChainInvolvementLink 
                            connect source ::> 'CDT_System Project'::'CDT_System'::'Logical Architecture'::'Logical Functions'::'Root Logical Function'.'Detect Concussion'.'8c0ea5ed-d270-4cb8-a6e8-3d53b4c28e83'
                            to  target ::> 'CDT_System Project'::'CDT_System'::'Logical Architecture'::'Logical Functions'::'Root Logical Function'.'Detect Concussion'.'d2220262-3839-40f3-85b5-2efeb1b2c315' {

                                ref :>> involved = 'CDT_System Project'::'CDT_System'::'Logical Architecture'::'Logical Functions'::'Root Logical Function'.'Device alerts possible Concussion'.'2ad3591e-5a1b-458d-be75-1a6f8a8b6aed';

                            } 
                        ref action '172cf76e-8faa-41a8-abef-c974a00ce85b' = 'CDT_System Project'::'CDT_System'::'Logical Architecture'::'Logical Functions'::'Root Logical Function'.'Device alerts possible Concussion'.'Record the Concussion'; 
                        connection 'c9f94f6d-a634-4b4b-9eed-be7d67f0b9d3' : FunctionalChainInvolvementLink 
                            connect source ::> 'CDT_System Project'::'CDT_System'::'Logical Architecture'::'Logical Functions'::'Root Logical Function'.'Detect Concussion'.'d2220262-3839-40f3-85b5-2efeb1b2c315'
                            to  target ::> 'CDT_System Project'::'CDT_System'::'Logical Architecture'::'Logical Functions'::'Root Logical Function'.'Detect Concussion'.'172cf76e-8faa-41a8-abef-c974a00ce85b' {

                                ref :>> involved = 'CDT_System Project'::'CDT_System'::'Logical Architecture'::'Logical Functions'::'Root Logical Function'.'Device alerts possible Concussion'.'45077ed7-3532-4a54-983a-4472bf80b75f';

                            } 
                        connection '8a4c7034-d3fe-400c-a514-898510cf2939' : FunctionalChainInvolvementLink 
                            connect source ::> 'CDT_System Project'::'CDT_System'::'Logical Architecture'::'Logical Functions'::'Root Logical Function'.'Detect Concussion'.'172cf76e-8faa-41a8-abef-c974a00ce85b'
                            to  target ::> 'CDT_System Project'::'CDT_System'::'Logical Architecture'::'Logical Functions'::'Root Logical Function'.'Detect Concussion'.'d8ca79bf-e32d-43d9-8d31-e70289d1c9a9' {

                                ref :>> involved = 'CDT_System Project'::'CDT_System'::'Logical Architecture'::'Logical Functions'::'Root Logical Function'.'Device alerts possible Concussion'.'d194214f-1ab1-443a-97ab-38dc1fe35d02';

                            } 
                        ref action '3572c696-a4df-4124-beaf-63cc9451e773' = 'CDT_System Project'::'CDT_System'::'Logical Architecture'::'Logical Functions'::'Root Logical Function'.'Data is Retrieved'.'Provide Hit Data'; 
                         
                    }  
                    action 'Aquire System' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outSystem' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outSystem ' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outSystem' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Logical Architecture'::'Logical Functions'::'Root Logical Function'.'Aquire System'.'outSystem',
                        'CDT_System Project'::'CDT_System'::'Logical Architecture'::'Logical Functions'::'Root Logical Function'.'Aquire System'.'outSystem ',
                        'CDT_System Project'::'CDT_System'::'Logical Architecture'::'Logical Functions'::'Root Logical Function'.'Aquire System'.'outSystem'); 
                         
                    }  
                    action 'Create profiles for Athletes' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inAthlete Data' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outProfile Data' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outAthlete Profile' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Create profiles for Athletes'.'inSystem',
                        'CDT_System Project'::'CDT_System'::'Logical Architecture'::'Logical Functions'::'Root Logical Function'.'Create profiles for Athletes'.'inAthlete Data'); 
                        ref :>> outputs =  ('CDT_System Project'::'CDT_System'::'Logical Architecture'::'Logical Functions'::'Root Logical Function'.'Create profiles for Athletes'.'outProfile Data',
                        'CDT_System Project'::'CDT_System'::'Logical Architecture'::'Logical Functions'::'Root Logical Function'.'Create profiles for Athletes'.'outAthlete Profile'); 
                         
                    }  
                    action 'Create Unique IDs for Athlete' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Initiate ID Creation' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inID' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Create Unique IDs for Athlete'.'Initiate ID Creation'.'inID'); 
                            ref :>> outputs =  ('CDT_System Project'::'CDT_System'::'Logical Architecture'::'Logical Functions'::'Root Logical Function'.'Create Unique IDs for Athlete'.'Initiate ID Creation'.'FOP 1'); 
                        }  
                        action 'Create ID' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            in port 'FIP 2' : FunctionInputPort  { 
                                attribute :>> isControlType = false; 
                                attribute :>> ordering = ObjectNodeOrderingKind::FIFO; 
                                attribute :>> isControl = false; 
                                attribute :>> kindOfNode = ObjectNodeKind::Unspecified; 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Create Unique IDs for Athlete'.'Create ID'.'FIP 1',
                            'CDT_System Project'::'CDT_System'::'Logical Architecture'::'Logical Functions'::'Root Logical Function'.'Create Unique IDs for Athlete'.'Create ID'.'FIP 2'); 
                            ref :>> outputs =  ('CDT_System Project'::'CDT_System'::'Logical Architecture'::'Logical Functions'::'Root Logical Function'.'Create Unique IDs for Athlete'.'Create ID'.'FOP 1'); 
                        }  
                        action 'Create and Program ID' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            out port 'outID Device' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Logical Architecture'::'Logical Functions'::'Root Logical Function'.'Create Unique IDs for Athlete'.'Create and Program ID'.'FIP 1'); 
                            ref :>> outputs =  ('CDT_System Project'::'CDT_System'::'Logical Architecture'::'Logical Functions'::'Root Logical Function'.'Create Unique IDs for Athlete'.'Create and Program ID'.'outID Device'); 
                        }  
                        interface '5c40769b-d826-496b-894d-6efeb8a0a5b5' : FunctionalExchange 
                            connect source ::> 'CDT_System Project'::'CDT_System'::'Logical Architecture'::'Logical Functions'::'Root Logical Function'.'Create Unique IDs for Athlete'.'Initiate ID Creation'.'FOP 1'
                            to target ::> 'CDT_System Project'::'CDT_System'::'Logical Architecture'::'Logical Functions'::'Root Logical Function'.'Create Unique IDs for Athlete'.'Create ID'.'FIP 1' { 
                            attribute :>> isMulticast = false; 
                            attribute :>> kindOfRate = RateKind::Unspecified; 
                            attribute :>> isMultireceive = false; 
                            attribute :>> interfaceName = "ID Create"; 
                        }  
                        interface '1974be04-a3fa-41df-b9e5-06ce4a06cb99' : FunctionalExchange 
                            connect source ::> 'CDT_System Project'::'CDT_System'::'Logical Architecture'::'Logical Functions'::'Root Logical Function'.'Create Unique IDs for Athlete'.'Create ID'.'FOP 1'
                            to target ::> 'CDT_System Project'::'CDT_System'::'Logical Architecture'::'Logical Functions'::'Root Logical Function'.'Create Unique IDs for Athlete'.'Create and Program ID'.'FIP 1' { 
                            attribute :>> isMulticast = false; 
                            attribute :>> kindOfRate = RateKind::Unspecified; 
                            attribute :>> isMultireceive = false; 
                            attribute :>> interfaceName = "Program"; 
                        }  
                        ref :>> ownedFunctions =  ('CDT_System Project'::'CDT_System'::'Logical Architecture'::'Logical Functions'::'Root Logical Function'.'Create Unique IDs for Athlete'.'Initiate ID Creation',
                        'CDT_System Project'::'CDT_System'::'Logical Architecture'::'Logical Functions'::'Root Logical Function'.'Create Unique IDs for Athlete'.'Create ID',
                        'CDT_System Project'::'CDT_System'::'Logical Architecture'::'Logical Functions'::'Root Logical Function'.'Create Unique IDs for Athlete'.'Create and Program ID'); 
                         
                        ref :>> ownedFunctionalExchanges =  ('CDT_System Project'::'CDT_System'::'Logical Architecture'::'Logical Functions'::'Root Logical Function'.'Create Unique IDs for Athlete'.'5c40769b-d826-496b-894d-6efeb8a0a5b5',
                        'CDT_System Project'::'CDT_System'::'Logical Architecture'::'Logical Functions'::'Root Logical Function'.'Create Unique IDs for Athlete'.'1974be04-a3fa-41df-b9e5-06ce4a06cb99'); 
                    }  
                    action 'Provide Data for Profile' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outAthlete Data' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Logical Architecture'::'Logical Functions'::'Root Logical Function'.'Provide Data for Profile'.'outAthlete Data'); 
                         
                    }  
                    action 'Recieve ID' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID Card' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Recieve ID'.'inID Card'); 
                        ref :>> outputs =  ('CDT_System Project'::'CDT_System'::'Logical Architecture'::'Logical Functions'::'Root Logical Function'.'Recieve ID'.'outID'); 
                         
                    }  
                    action 'Store Profile' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Gather Profile Data' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inAthlete Profile' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Store Profile'.'Gather Profile Data'.'inAthlete Profile'); 
                            ref :>> outputs =  ('CDT_System Project'::'CDT_System'::'Logical Architecture'::'Logical Functions'::'Root Logical Function'.'Store Profile'.'Gather Profile Data'.'FOP 1'); 
                        }  
                        action 'Store Profile' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Store Profile'.'Store Profile'.'FIP 1'); 
                            ref :>> outputs =  ('CDT_System Project'::'CDT_System'::'Logical Architecture'::'Logical Functions'::'Root Logical Function'.'Store Profile'.'Store Profile'.'FOP 1'); 
                        }  
                        interface '4614f066-5aa3-4b81-a308-99d5a57d3889' : FunctionalExchange 
                            connect source ::> 'CDT_System Project'::'CDT_System'::'Logical Architecture'::'Logical Functions'::'Root Logical Function'.'Store Profile'.'Gather Profile Data'.'FOP 1'
                            to target ::> 'CDT_System Project'::'CDT_System'::'Logical Architecture'::'Logical Functions'::'Root Logical Function'.'Store Profile'.'Store Profile'.'FIP 1' { 
                            attribute :>> isMulticast = false; 
                            attribute :>> kindOfRate = RateKind::Unspecified; 
                            attribute :>> isMultireceive = false; 
                            attribute :>> interfaceName = "Profile Data"; 
                        }  
                        ref :>> ownedFunctions =  ('CDT_System Project'::'CDT_System'::'Logical Architecture'::'Logical Functions'::'Root Logical Function'.'Store Profile'.'Gather Profile Data',
                        'CDT_System Project'::'CDT_System'::'Logical Architecture'::'Logical Functions'::'Root Logical Function'.'Store Profile'.'Store Profile'); 
                         
                        ref :>> ownedFunctionalExchanges =  ('CDT_System Project'::'CDT_System'::'Logical Architecture'::'Logical Functions'::'Root Logical Function'.'Store Profile'.'4614f066-5aa3-4b81-a308-99d5a57d3889'); 
                    }  
                    action 'Create Unique IDs' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inProfile Data' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Create Unique IDs'.'inProfile Data'); 
                        ref :>> outputs =  ('CDT_System Project'::'CDT_System'::'Logical Architecture'::'Logical Functions'::'Root Logical Function'.'Create Unique IDs'.'outID'); 
                         
                    }  
                    action 'Provide ID to Athlete' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID Device' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outID Card' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Provide ID to Athlete'.'inID Device'); 
                        ref :>> outputs =  ('CDT_System Project'::'CDT_System'::'Logical Architecture'::'Logical Functions'::'Root Logical Function'.'Provide ID to Athlete'.'outID Card'); 
                         
                    }  
                    action 'Assemble System Components' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inhelmut mounting' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'insensor mounting' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outAssembled System' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Assemble System Components'.'inSystem',
                        'CDT_System Project'::'CDT_System'::'Logical Architecture'::'Logical Functions'::'Root Logical Function'.'Assemble System Components'.'inhelmut mounting',
                        'CDT_System Project'::'CDT_System'::'Logical Architecture'::'Logical Functions'::'Root Logical Function'.'Assemble System Components'.'insensor mounting'); 
                        ref :>> outputs =  ('CDT_System Project'::'CDT_System'::'Logical Architecture'::'Logical Functions'::'Root Logical Function'.'Assemble System Components'.'outAssembled System'); 
                         
                    }  
                    action 'Provide access to helmut mounting' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outhelmut mounting' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Logical Architecture'::'Logical Functions'::'Root Logical Function'.'Provide access to helmut mounting'.'outhelmut mounting'); 
                         
                    }  
                    action 'Provide access to sensing device mounting' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outsensor mounting' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Logical Architecture'::'Logical Functions'::'Root Logical Function'.'Provide access to sensing device mounting'.'outsensor mounting'); 
                         
                    }  
                    action 'Prep the device for use' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAssembled System' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Prep the device for use'.'inAssembled System'); 
                         
                    }  
                    action 'Insert ID into Sensing Device' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outReady to put on Helmut' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Insert ID into Sensing Device'.'inID'); 
                        ref :>> outputs =  ('CDT_System Project'::'CDT_System'::'Logical Architecture'::'Logical Functions'::'Root Logical Function'.'Insert ID into Sensing Device'.'outReady to put on Helmut',
                        'CDT_System Project'::'CDT_System'::'Logical Architecture'::'Logical Functions'::'Root Logical Function'.'Insert ID into Sensing Device'.'outID'); 
                         
                    }  
                    action 'Recieve ID' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outAthlete ID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Recieve ID'.'inID'); 
                        ref :>> outputs =  ('CDT_System Project'::'CDT_System'::'Logical Architecture'::'Logical Functions'::'Root Logical Function'.'Recieve ID'.'outAthlete ID'); 
                         
                    }  
                    action 'Device alerts possible Concussion' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Send message' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inConcussion' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                ref :>> outgoingExchangeItems =  ('CDT_System Project'::'CDT_System'::'Operational Analysis'::'Data'::'Alert'); 
                            }  
                            ref :>> inputs =  ('CDT_System Project'::'CDT_System'::'Logical Architecture'::'Logical Functions'::'Root Logical Function'.'Device alerts possible Concussion'.'Send message'.'inConcussion'); 
                            ref :>> outputs =  ('CDT_System Project'::'CDT_System'::'Logical Architecture'::'Logical Functions'::'Root Logical Function'.'Device alerts possible Concussion'.'Send message'.'FOP 1'); 
                        }  
                        action 'Relay message' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Alert'); 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                ref :>> outgoingExchangeItems =  ('CDT_System Project'::'CDT_System'::'Operational Analysis'::'Data'::'Alert'); 
                            }  
                            ref :>> inputs =  ('CDT_System Project'::'CDT_System'::'Logical Architecture'::'Logical Functions'::'Root Logical Function'.'Device alerts possible Concussion'.'Relay message'.'FIP 1'); 
                            ref :>> outputs =  ('CDT_System Project'::'CDT_System'::'Logical Architecture'::'Logical Functions'::'Root Logical Function'.'Device alerts possible Concussion'.'Relay message'.'FOP 1'); 
                        }  
                        action 'Record the Concussion' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Alert'); 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                                ref :>> outgoingExchangeItems =  ('CDT_System Project'::'CDT_System'::'Operational Analysis'::'Data'::'Alert'); 
                            }  
                            ref :>> inputs =  ('CDT_System Project'::'CDT_System'::'Logical Architecture'::'Logical Functions'::'Root Logical Function'.'Device alerts possible Concussion'.'Record the Concussion'.'FIP 1'); 
                            ref :>> outputs =  ('CDT_System Project'::'CDT_System'::'Logical Architecture'::'Logical Functions'::'Root Logical Function'.'Device alerts possible Concussion'.'Record the Concussion'.'FOP 2'); 
                        }  
                        action 'Alert the Training' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Alert'); 
                            }  
                            out port 'outConcussion Alert to Trainer' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Operational Analysis'::'Data'::'Alert'); 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Device alerts possible Concussion'.'Alert the Training'.'FIP 1'); 
                            ref :>> outputs =  ('CDT_System Project'::'CDT_System'::'Logical Architecture'::'Logical Functions'::'Root Logical Function'.'Device alerts possible Concussion'.'Alert the Training'.'outConcussion Alert to Trainer',
                            'CDT_System Project'::'CDT_System'::'Logical Architecture'::'Logical Functions'::'Root Logical Function'.'Device alerts possible Concussion'.'Alert the Training'.'FOP 2'); 
                        }  
                        interface '2ad3591e-5a1b-458d-be75-1a6f8a8b6aed' : FunctionalExchange 
                            connect source ::> 'CDT_System Project'::'CDT_System'::'Logical Architecture'::'Logical Functions'::'Root Logical Function'.'Device alerts possible Concussion'.'Send message'.'FOP 1'
                            to target ::> 'CDT_System Project'::'CDT_System'::'Logical Architecture'::'Logical Functions'::'Root Logical Function'.'Device alerts possible Concussion'.'Relay message'.'FIP 1' { 
                            attribute :>> isMulticast = false; 
                            attribute :>> kindOfRate = RateKind::Unspecified; 
                            attribute :>> isMultireceive = false; 
                            attribute :>> interfaceName = "Concussion Message"; 
                            ref :>> exchangedItems =  ('CDT_System Project'::'CDT_System'::'Operational Analysis'::'Data'::'Alert'); 
                        }  
                        interface '45077ed7-3532-4a54-983a-4472bf80b75f' : FunctionalExchange 
                            connect source ::> 'CDT_System Project'::'CDT_System'::'Logical Architecture'::'Logical Functions'::'Root Logical Function'.'Device alerts possible Concussion'.'Relay message'.'FOP 1'
                            to target ::> 'CDT_System Project'::'CDT_System'::'Logical Architecture'::'Logical Functions'::'Root Logical Function'.'Device alerts possible Concussion'.'Record the Concussion'.'FIP 1' { 
                            attribute :>> isMulticast = false; 
                            attribute :>> kindOfRate = RateKind::Unspecified; 
                            attribute :>> isMultireceive = false; 
                            attribute :>> interfaceName = "Concussion Message"; 
                            ref :>> exchangedItems =  ('CDT_System Project'::'CDT_System'::'Operational Analysis'::'Data'::'Alert'); 
                        }  
                        interface 'd194214f-1ab1-443a-97ab-38dc1fe35d02' : FunctionalExchange 
                            connect source ::> 'CDT_System Project'::'CDT_System'::'Logical Architecture'::'Logical Functions'::'Root Logical Function'.'Device alerts possible Concussion'.'Record the Concussion'.'FOP 2'
                            to target ::> 'CDT_System Project'::'CDT_System'::'Logical Architecture'::'Logical Functions'::'Root Logical Function'.'Device alerts possible Concussion'.'Alert the Training'.'FIP 1' { 
                            attribute :>> isMulticast = false; 
                            attribute :>> kindOfRate = RateKind::Unspecified; 
                            attribute :>> isMultireceive = false; 
                            attribute :>> interfaceName = "Concussion Alert"; 
                            ref :>> exchangedItems =  ('CDT_System Project'::'CDT_System'::'Operational Analysis'::'Data'::'Alert'); 
                        }  
                        ref :>> ownedFunctions =  ('CDT_System Project'::'CDT_System'::'Logical Architecture'::'Logical Functions'::'Root Logical Function'.'Device alerts possible Concussion'.'Send message',
                        'CDT_System Project'::'CDT_System'::'Logical Architecture'::'Logical Functions'::'Root Logical Function'.'Device alerts possible Concussion'.'Relay message',
                        'CDT_System Project'::'CDT_System'::'Logical Architecture'::'Logical Functions'::'Root Logical Function'.'Device alerts possible Concussion'.'Record the Concussion',
                        'CDT_System Project'::'CDT_System'::'Logical Architecture'::'Logical Functions'::'Root Logical Function'.'Device alerts possible Concussion'.'Alert the Training'); 
                         
                        ref :>> ownedFunctionalExchanges =  ('CDT_System Project'::'CDT_System'::'Logical Architecture'::'Logical Functions'::'Root Logical Function'.'Device alerts possible Concussion'.'2ad3591e-5a1b-458d-be75-1a6f8a8b6aed',
                        'CDT_System Project'::'CDT_System'::'Logical Architecture'::'Logical Functions'::'Root Logical Function'.'Device alerts possible Concussion'.'45077ed7-3532-4a54-983a-4472bf80b75f',
                        'CDT_System Project'::'CDT_System'::'Logical Architecture'::'Logical Functions'::'Root Logical Function'.'Device alerts possible Concussion'.'d194214f-1ab1-443a-97ab-38dc1fe35d02'); 
                    }  
                    action 'Trainer Recieves Concussion Alert' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inConcussion Policy' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inConcussion Alert to Trainer' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Alert'); 
                             
                        }  
                        out port 'outAlert' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'FOP 2' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Logical Architecture'::'Logical Functions'::'Root Logical Function'.'Trainer Recieves Concussion Alert'.'inConcussion Policy',
                        'CDT_System Project'::'CDT_System'::'Logical Architecture'::'Logical Functions'::'Root Logical Function'.'Trainer Recieves Concussion Alert'.'inConcussion Alert to Trainer'); 
                        ref :>> outputs =  ('CDT_System Project'::'CDT_System'::'Logical Architecture'::'Logical Functions'::'Root Logical Function'.'Trainer Recieves Concussion Alert'.'outAlert',
                        'CDT_System Project'::'CDT_System'::'Logical Architecture'::'Logical Functions'::'Root Logical Function'.'Trainer Recieves Concussion Alert'.'FOP 2'); 
                         
                    }  
                    action 'Device records Hit' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inHit' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Hit'); 
                             
                        }  
                        out port 'outConcussion' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outStored Data' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Device records Hit'.'inHit'); 
                        ref :>> outputs =  ('CDT_System Project'::'CDT_System'::'Logical Architecture'::'Logical Functions'::'Root Logical Function'.'Device records Hit'.'outConcussion',
                        'CDT_System Project'::'CDT_System'::'Logical Architecture'::'Logical Functions'::'Root Logical Function'.'Device records Hit'.'outStored Data'); 
                         
                    }  
                    action 'Enable Secure Collection' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete ID' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inDevice ID ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outSensor Ready' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Enable Secure Collection'.'inAthlete ID',
                        'CDT_System Project'::'CDT_System'::'Logical Architecture'::'Logical Functions'::'Root Logical Function'.'Enable Secure Collection'.'inDevice ID '); 
                        ref :>> outputs =  ('CDT_System Project'::'CDT_System'::'Logical Architecture'::'Logical Functions'::'Root Logical Function'.'Enable Secure Collection'.'outSensor Ready'); 
                         
                    }  
                    action 'Place on Helmut' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inReady to put on Helmut' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outHead ' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Place on Helmut'.'inReady to put on Helmut'); 
                        ref :>> outputs =  ('CDT_System Project'::'CDT_System'::'Logical Architecture'::'Logical Functions'::'Root Logical Function'.'Place on Helmut'.'outHead '); 
                         
                    }  
                    action 'Device' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                         
                    }  
                    action 'Provide ID Information' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outDevice ID ' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Logical Architecture'::'Logical Functions'::'Root Logical Function'.'Provide ID Information'.'outDevice ID '); 
                         
                    }  
                    action 'Athlete Particpates in Activity' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outActivity' : FunctionOutputPort  { 
                            attribute :>> isControlType = false; 
                            attribute :>> ordering = ObjectNodeOrderingKind::FIFO; 
                            attribute :>> isControl = false; 
                            attribute :>> kindOfNode = ObjectNodeKind::Unspecified; 
                             
                            ref :>> outgoingExchangeItems =  ('CDT_System Project'::'CDT_System'::'Operational Analysis'::'Data'::'Hit'); 
                        }  
                        ref :>> outputs =  ('CDT_System Project'::'CDT_System'::'Logical Architecture'::'Logical Functions'::'Root Logical Function'.'Athlete Particpates in Activity'.'outActivity'); 
                         
                    }  
                    action 'Yield to Evaluation' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAlert' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outEvaluation' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Yield to Evaluation'.'inAlert'); 
                        ref :>> outputs =  ('CDT_System Project'::'CDT_System'::'Logical Architecture'::'Logical Functions'::'Root Logical Function'.'Yield to Evaluation'.'outEvaluation'); 
                         
                    }  
                    action 'Receive Athlete ' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inHead ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outHelmut Motion' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Receive Athlete '.'inHead '); 
                        ref :>> outputs =  ('CDT_System Project'::'CDT_System'::'Logical Architecture'::'Logical Functions'::'Root Logical Function'.'Receive Athlete '.'outHelmut Motion'); 
                         
                    }  
                    action 'Data is Retrieved' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Intitate Data Retrieval' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            in port 'FIP 2' : FunctionInputPort  { 
                                attribute :>> isControlType = false; 
                                attribute :>> ordering = ObjectNodeOrderingKind::FIFO; 
                                attribute :>> isControl = false; 
                                attribute :>> kindOfNode = ObjectNodeKind::Unspecified; 
                            }  
                            in port 'inEvaluation' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                ref :>> outgoingExchangeItems =  ('CDT_System Project'::'CDT_System'::'Operational Analysis'::'Data'::'Concussion Data'); 
                            }  
                            out port 'outRecorded Data' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Operational Analysis'::'Data'::'Concussion Data'); 
                            }  
                            ref :>> inputs =  ('CDT_System Project'::'CDT_System'::'Logical Architecture'::'Logical Functions'::'Root Logical Function'.'Data is Retrieved'.'Intitate Data Retrieval'.'FIP 1',
                            'CDT_System Project'::'CDT_System'::'Logical Architecture'::'Logical Functions'::'Root Logical Function'.'Data is Retrieved'.'Intitate Data Retrieval'.'FIP 2',
                            'CDT_System Project'::'CDT_System'::'Logical Architecture'::'Logical Functions'::'Root Logical Function'.'Data is Retrieved'.'Intitate Data Retrieval'.'inEvaluation'); 
                            ref :>> outputs =  ('CDT_System Project'::'CDT_System'::'Logical Architecture'::'Logical Functions'::'Root Logical Function'.'Data is Retrieved'.'Intitate Data Retrieval'.'FOP 1',
                            'CDT_System Project'::'CDT_System'::'Logical Architecture'::'Logical Functions'::'Root Logical Function'.'Data is Retrieved'.'Intitate Data Retrieval'.'outRecorded Data'); 
                        }  
                        action 'Request the Data ' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Concussion Data'); 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Data is Retrieved'.'Request the Data '.'FIP 1'); 
                            ref :>> outputs =  ('CDT_System Project'::'CDT_System'::'Logical Architecture'::'Logical Functions'::'Root Logical Function'.'Data is Retrieved'.'Request the Data '.'FOP 1'); 
                        }  
                        action 'Provide Hit Data' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            in port 'inStored Data' : FunctionInputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Logical Architecture'::'Logical Functions'::'Root Logical Function'.'Data is Retrieved'.'Provide Hit Data'.'FIP 1',
                            'CDT_System Project'::'CDT_System'::'Logical Architecture'::'Logical Functions'::'Root Logical Function'.'Data is Retrieved'.'Provide Hit Data'.'inStored Data'); 
                        }  
                        interface 'c667cdb0-6ba8-4c8d-b6aa-52cec107730e' : FunctionalExchange 
                            connect source ::> 'CDT_System Project'::'CDT_System'::'Logical Architecture'::'Logical Functions'::'Root Logical Function'.'Data is Retrieved'.'Intitate Data Retrieval'.'FOP 1'
                            to target ::> 'CDT_System Project'::'CDT_System'::'Logical Architecture'::'Logical Functions'::'Root Logical Function'.'Data is Retrieved'.'Request the Data '.'FIP 1' { 
                            attribute :>> isMulticast = false; 
                            attribute :>> kindOfRate = RateKind::Unspecified; 
                            attribute :>> isMultireceive = false; 
                            attribute :>> interfaceName = "Data Request"; 
                            ref :>> exchangedItems =  ('CDT_System Project'::'CDT_System'::'Operational Analysis'::'Data'::'Concussion Data'); 
                        }  
                        interface 'b63a6c42-4adc-4f2d-bbb7-8a230c7a9862' : FunctionalExchange 
                            connect source ::> 'CDT_System Project'::'CDT_System'::'Logical Architecture'::'Logical Functions'::'Root Logical Function'.'Data is Retrieved'.'Request the Data '.'FOP 1'
                            to target ::> 'CDT_System Project'::'CDT_System'::'Logical Architecture'::'Logical Functions'::'Root Logical Function'.'Data is Retrieved'.'Provide Hit Data'.'FIP 1' { 
                            attribute :>> isMulticast = false; 
                            attribute :>> kindOfRate = RateKind::Unspecified; 
                            attribute :>> isMultireceive = false; 
                            attribute :>> interfaceName = "Request"; 
                            ref :>> exchangedItems =  ('CDT_System Project'::'CDT_System'::'Operational Analysis'::'Data'::'Concussion Data'); 
                        }  
                        ref :>> ownedFunctions =  ('CDT_System Project'::'CDT_System'::'Logical Architecture'::'Logical Functions'::'Root Logical Function'.'Data is Retrieved'.'Intitate Data Retrieval',
                        'CDT_System Project'::'CDT_System'::'Logical Architecture'::'Logical Functions'::'Root Logical Function'.'Data is Retrieved'.'Request the Data ',
                        'CDT_System Project'::'CDT_System'::'Logical Architecture'::'Logical Functions'::'Root Logical Function'.'Data is Retrieved'.'Provide Hit Data'); 
                         
                        ref :>> ownedFunctionalExchanges =  ('CDT_System Project'::'CDT_System'::'Logical Architecture'::'Logical Functions'::'Root Logical Function'.'Data is Retrieved'.'c667cdb0-6ba8-4c8d-b6aa-52cec107730e',
                        'CDT_System Project'::'CDT_System'::'Logical Architecture'::'Logical Functions'::'Root Logical Function'.'Data is Retrieved'.'b63a6c42-4adc-4f2d-bbb7-8a230c7a9862'); 
                    }  
                    action 'Enable Monitoring' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Relay Enabled Message' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Enable Monitoring'.'Relay Enabled Message'.'FIP 1'); 
                            ref :>> outputs =  ('CDT_System Project'::'CDT_System'::'Logical Architecture'::'Logical Functions'::'Root Logical Function'.'Enable Monitoring'.'Relay Enabled Message'.'FOP 1'); 
                        }  
                        action 'Enable Monitoring' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inSensor Ready' : FunctionInputPort  { 
                                attribute :>> isControlType = false; 
                                attribute :>> ordering = ObjectNodeOrderingKind::FIFO; 
                                attribute :>> isControl = false; 
                                attribute :>> kindOfNode = ObjectNodeKind::Unspecified; 
                                 
                            }  
                            in port 'inHelmut Motion' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Enable Monitoring'.'Enable Monitoring'.'inSensor Ready',
                            'CDT_System Project'::'CDT_System'::'Logical Architecture'::'Logical Functions'::'Root Logical Function'.'Enable Monitoring'.'Enable Monitoring'.'inHelmut Motion'); 
                            ref :>> outputs =  ('CDT_System Project'::'CDT_System'::'Logical Architecture'::'Logical Functions'::'Root Logical Function'.'Enable Monitoring'.'Enable Monitoring'.'FOP 1',
                            'CDT_System Project'::'CDT_System'::'Logical Architecture'::'Logical Functions'::'Root Logical Function'.'Enable Monitoring'.'Enable Monitoring'.'FOP 2'); 
                        }  
                        action 'Enable Recored' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Enable Monitoring'.'Enable Recored'.'FIP 1'); 
                            ref :>> outputs =  ('CDT_System Project'::'CDT_System'::'Logical Architecture'::'Logical Functions'::'Root Logical Function'.'Enable Monitoring'.'Enable Recored'.'FOP 1'); 
                        }  
                        action 'Enable Indicated' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            out port 'outEnable Signal' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Enable Monitoring'.'Enable Indicated'.'FIP 1'); 
                            ref :>> outputs =  ('CDT_System Project'::'CDT_System'::'Logical Architecture'::'Logical Functions'::'Root Logical Function'.'Enable Monitoring'.'Enable Indicated'.'outEnable Signal',
                            'CDT_System Project'::'CDT_System'::'Logical Architecture'::'Logical Functions'::'Root Logical Function'.'Enable Monitoring'.'Enable Indicated'.'FOP 2'); 
                        }  
                        action 'Enable Bluetoth Connect' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Enable Monitoring'.'Enable Bluetoth Connect'.'FIP 1'); 
                            ref :>> outputs =  ('CDT_System Project'::'CDT_System'::'Logical Architecture'::'Logical Functions'::'Root Logical Function'.'Enable Monitoring'.'Enable Bluetoth Connect'.'FOP 1'); 
                        }  
                        action 'Look for bluetooth connect' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                            }  
                            in port 'FIP 2' : FunctionInputPort  { 
                                attribute :>> isControlType = false; 
                                attribute :>> ordering = ObjectNodeOrderingKind::FIFO; 
                                attribute :>> isControl = false; 
                                attribute :>> kindOfNode = ObjectNodeKind::Unspecified; 
                            }  
                            ref :>> inputs =  ('CDT_System Project'::'CDT_System'::'Logical Architecture'::'Logical Functions'::'Root Logical Function'.'Enable Monitoring'.'Look for bluetooth connect'.'FIP 1',
                            'CDT_System Project'::'CDT_System'::'Logical Architecture'::'Logical Functions'::'Root Logical Function'.'Enable Monitoring'.'Look for bluetooth connect'.'FIP 2'); 
                        }  
                        interface 'ed518be9-43ff-4d81-b589-3a8c39857811' : FunctionalExchange 
                            connect source ::> 'CDT_System Project'::'CDT_System'::'Logical Architecture'::'Logical Functions'::'Root Logical Function'.'Enable Monitoring'.'Enable Monitoring'.'FOP 1'
                            to target ::> 'CDT_System Project'::'CDT_System'::'Logical Architecture'::'Logical Functions'::'Root Logical Function'.'Enable Monitoring'.'Relay Enabled Message'.'FIP 1' { 
                            attribute :>> isMulticast = false; 
                            attribute :>> kindOfRate = RateKind::Unspecified; 
                            attribute :>> isMultireceive = false; 
                            attribute :>> interfaceName = "Enable Signal"; 
                        }  
                        interface '346ba0de-117f-4838-bd24-1b822d200e79' : FunctionalExchange 
                            connect source ::> 'CDT_System Project'::'CDT_System'::'Logical Architecture'::'Logical Functions'::'Root Logical Function'.'Enable Monitoring'.'Relay Enabled Message'.'FOP 1'
                            to target ::> 'CDT_System Project'::'CDT_System'::'Logical Architecture'::'Logical Functions'::'Root Logical Function'.'Enable Monitoring'.'Enable Recored'.'FIP 1' { 
                            attribute :>> isMulticast = false; 
                            attribute :>> kindOfRate = RateKind::Unspecified; 
                            attribute :>> isMultireceive = false; 
                            attribute :>> interfaceName = "Enable"; 
                        }  
                        interface '6bc089b3-336d-4890-a903-ab77f625b6e0' : FunctionalExchange 
                            connect source ::> 'CDT_System Project'::'CDT_System'::'Logical Architecture'::'Logical Functions'::'Root Logical Function'.'Enable Monitoring'.'Enable Recored'.'FOP 1'
                            to target ::> 'CDT_System Project'::'CDT_System'::'Logical Architecture'::'Logical Functions'::'Root Logical Function'.'Enable Monitoring'.'Enable Indicated'.'FIP 1' { 
                            attribute :>> isMulticast = false; 
                            attribute :>> kindOfRate = RateKind::Unspecified; 
                            attribute :>> isMultireceive = false; 
                            attribute :>> interfaceName = "Enable"; 
                        }  
                        interface 'c0f41030-26d8-4248-b51e-cc0d0bd5ba25' : FunctionalExchange 
                            connect source ::> 'CDT_System Project'::'CDT_System'::'Logical Architecture'::'Logical Functions'::'Root Logical Function'.'Enable Monitoring'.'Enable Monitoring'.'FOP 2'
                            to target ::> 'CDT_System Project'::'CDT_System'::'Logical Architecture'::'Logical Functions'::'Root Logical Function'.'Enable Monitoring'.'Look for bluetooth connect'.'FIP 1' { 
                            attribute :>> isMulticast = false; 
                            attribute :>> kindOfRate = RateKind::Unspecified; 
                            attribute :>> isMultireceive = false; 
                            attribute :>> interfaceName = "Bluetooth ready"; 
                        }  
                        interface '2c13b94c-54bc-4937-b982-6e5870f616af' : FunctionalExchange 
                            connect source ::> 'CDT_System Project'::'CDT_System'::'Logical Architecture'::'Logical Functions'::'Root Logical Function'.'Enable Monitoring'.'Enable Indicated'.'FOP 2'
                            to target ::> 'CDT_System Project'::'CDT_System'::'Logical Architecture'::'Logical Functions'::'Root Logical Function'.'Enable Monitoring'.'Enable Bluetoth Connect'.'FIP 1' { 
                            attribute :>> isMulticast = false; 
                            attribute :>> kindOfRate = RateKind::Unspecified; 
                            attribute :>> isMultireceive = false; 
                            attribute :>> interfaceName = "Confirm Bluetoth"; 
                        }  
                        interface 'dab7038c-c1c1-441a-ac01-772653b7c3a4' : FunctionalExchange 
                            connect source ::> 'CDT_System Project'::'CDT_System'::'Logical Architecture'::'Logical Functions'::'Root Logical Function'.'Enable Monitoring'.'Enable Bluetoth Connect'.'FOP 1'
                            to target ::> 'CDT_System Project'::'CDT_System'::'Logical Architecture'::'Logical Functions'::'Root Logical Function'.'Enable Monitoring'.'Look for bluetooth connect'.'FIP 2' { 
                            attribute :>> isMulticast = false; 
                            attribute :>> kindOfRate = RateKind::Unspecified; 
                            attribute :>> isMultireceive = false; 
                            attribute :>> interfaceName = "Connect "; 
                        }  
                        ref :>> ownedFunctions =  ('CDT_System Project'::'CDT_System'::'Logical Architecture'::'Logical Functions'::'Root Logical Function'.'Enable Monitoring'.'Relay Enabled Message',
                        'CDT_System Project'::'CDT_System'::'Logical Architecture'::'Logical Functions'::'Root Logical Function'.'Enable Monitoring'.'Enable Monitoring',
                        'CDT_System Project'::'CDT_System'::'Logical Architecture'::'Logical Functions'::'Root Logical Function'.'Enable Monitoring'.'Enable Recored',
                        'CDT_System Project'::'CDT_System'::'Logical Architecture'::'Logical Functions'::'Root Logical Function'.'Enable Monitoring'.'Enable Indicated',
                        'CDT_System Project'::'CDT_System'::'Logical Architecture'::'Logical Functions'::'Root Logical Function'.'Enable Monitoring'.'Enable Bluetoth Connect',
                        'CDT_System Project'::'CDT_System'::'Logical Architecture'::'Logical Functions'::'Root Logical Function'.'Enable Monitoring'.'Look for bluetooth connect'); 
                         
                        ref :>> ownedFunctionalExchanges =  ('CDT_System Project'::'CDT_System'::'Logical Architecture'::'Logical Functions'::'Root Logical Function'.'Enable Monitoring'.'ed518be9-43ff-4d81-b589-3a8c39857811',
                        'CDT_System Project'::'CDT_System'::'Logical Architecture'::'Logical Functions'::'Root Logical Function'.'Enable Monitoring'.'346ba0de-117f-4838-bd24-1b822d200e79',
                        'CDT_System Project'::'CDT_System'::'Logical Architecture'::'Logical Functions'::'Root Logical Function'.'Enable Monitoring'.'6bc089b3-336d-4890-a903-ab77f625b6e0',
                        'CDT_System Project'::'CDT_System'::'Logical Architecture'::'Logical Functions'::'Root Logical Function'.'Enable Monitoring'.'c0f41030-26d8-4248-b51e-cc0d0bd5ba25',
                        'CDT_System Project'::'CDT_System'::'Logical Architecture'::'Logical Functions'::'Root Logical Function'.'Enable Monitoring'.'2c13b94c-54bc-4937-b982-6e5870f616af',
                        'CDT_System Project'::'CDT_System'::'Logical Architecture'::'Logical Functions'::'Root Logical Function'.'Enable Monitoring'.'dab7038c-c1c1-441a-ac01-772653b7c3a4'); 
                    }  
                    action 'Recieve Enabled Signal from Athelete Helmut' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inEnable Signal' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Recieve Enabled Signal from Athelete Helmut'.'inEnable Signal'); 
                         
                    }  
                    action 'Data stored' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Data Stored' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inRecorded Data' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Concussion Data'); 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                ref :>> outgoingExchangeItems =  ('CDT_System Project'::'CDT_System'::'Operational Analysis'::'Data'::'Concussion Data'); 
                            }  
                            ref :>> inputs =  ('CDT_System Project'::'CDT_System'::'Logical Architecture'::'Logical Functions'::'Root Logical Function'.'Data stored'.'Data Stored'.'inRecorded Data'); 
                            ref :>> outputs =  ('CDT_System Project'::'CDT_System'::'Logical Architecture'::'Logical Functions'::'Root Logical Function'.'Data stored'.'Data Stored'.'FOP 1'); 
                        }  
                        action 'Data is Presented' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Concussion Data'); 
                            }  
                            out port 'outStored Data ' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Operational Analysis'::'Data'::'Concussion Data'); 
                            }  
                            ref :>> inputs =  ('CDT_System Project'::'CDT_System'::'Logical Architecture'::'Logical Functions'::'Root Logical Function'.'Data stored'.'Data is Presented'.'FIP 1'); 
                            ref :>> outputs =  ('CDT_System Project'::'CDT_System'::'Logical Architecture'::'Logical Functions'::'Root Logical Function'.'Data stored'.'Data is Presented'.'outStored Data '); 
                        }  
                        interface '062e99f3-77a8-4aff-8249-e8b8a460a254' : FunctionalExchange 
                            connect source ::> 'CDT_System Project'::'CDT_System'::'Logical Architecture'::'Logical Functions'::'Root Logical Function'.'Data stored'.'Data Stored'.'FOP 1'
                            to target ::> 'CDT_System Project'::'CDT_System'::'Logical Architecture'::'Logical Functions'::'Root Logical Function'.'Data stored'.'Data is Presented'.'FIP 1' { 
                            attribute :>> isMulticast = false; 
                            attribute :>> kindOfRate = RateKind::Unspecified; 
                            attribute :>> isMultireceive = false; 
                            attribute :>> interfaceName = "Data"; 
                            ref :>> exchangedItems =  ('CDT_System Project'::'CDT_System'::'Operational Analysis'::'Data'::'Concussion Data'); 
                        }  
                        ref :>> ownedFunctions =  ('CDT_System Project'::'CDT_System'::'Logical Architecture'::'Logical Functions'::'Root Logical Function'.'Data stored'.'Data Stored',
                        'CDT_System Project'::'CDT_System'::'Logical Architecture'::'Logical Functions'::'Root Logical Function'.'Data stored'.'Data is Presented'); 
                         
                        ref :>> ownedFunctionalExchanges =  ('CDT_System Project'::'CDT_System'::'Logical Architecture'::'Logical Functions'::'Root Logical Function'.'Data stored'.'062e99f3-77a8-4aff-8249-e8b8a460a254'); 
                    }  
                    action 'Data can be reviewed' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inStored Data ' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Concussion Data'); 
                             
                        }  
                        out port 'outInteraction 26' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Data can be reviewed'.'inStored Data '); 
                        ref :>> outputs =  ('CDT_System Project'::'CDT_System'::'Logical Architecture'::'Logical Functions'::'Root Logical Function'.'Data can be reviewed'.'outInteraction 26'); 
                         
                    }  
                    action 'Report Received' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inInstition Report' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Report'); 
                             
                        }  
                        ref :>> inputs =  ('CDT_System Project'::'CDT_System'::'Logical Architecture'::'Logical Functions'::'Root Logical Function'.'Report Received'.'inInstition Report'); 
                         
                    }  
                    action 'Report Received' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete Report' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Report'); 
                             
                        }  
                        ref :>> inputs =  ('CDT_System Project'::'CDT_System'::'Logical Architecture'::'Logical Functions'::'Root Logical Function'.'Report Received'.'inAthlete Report'); 
                         
                    }  
                    action 'Report received' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inParen Report' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Report'); 
                             
                        }  
                        ref :>> inputs =  ('CDT_System Project'::'CDT_System'::'Logical Architecture'::'Logical Functions'::'Root Logical Function'.'Report received'.'inParen Report'); 
                         
                    }  
                    action 'Executes Policies' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inInteraction 26' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outExecute Policy' : FunctionOutputPort  { 
                            attribute :>> isControlType = false; 
                            attribute :>> ordering = ObjectNodeOrderingKind::FIFO; 
                            attribute :>> isControl = false; 
                            attribute :>> kindOfNode = ObjectNodeKind::Unspecified; 
                             
                            ref :>> outgoingExchangeItems =  ('CDT_System Project'::'CDT_System'::'Operational Analysis'::'Data'::'Policy'); 
                        }  
                        ref :>> inputs =  ('CDT_System Project'::'CDT_System'::'Logical Architecture'::'Logical Functions'::'Root Logical Function'.'Executes Policies'.'inInteraction 26'); 
                        ref :>> outputs =  ('CDT_System Project'::'CDT_System'::'Logical Architecture'::'Logical Functions'::'Root Logical Function'.'Executes Policies'.'outExecute Policy'); 
                         
                    }  
                    action 'Established Concussion Policy' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outConcussion Policy' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Logical Architecture'::'Logical Functions'::'Root Logical Function'.'Established Concussion Policy'.'inSystem '); 
                        ref :>> outputs =  ('CDT_System Project'::'CDT_System'::'Logical Architecture'::'Logical Functions'::'Root Logical Function'.'Established Concussion Policy'.'outConcussion Policy'); 
                         
                    }  
                    action 'Generates Reports' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Request Report to be sent' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inExecute Policy' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Policy'); 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                ref :>> outgoingExchangeItems =  ('CDT_System Project'::'CDT_System'::'Operational Analysis'::'Data'::'Report'); 
                            }  
                            ref :>> inputs =  ('CDT_System Project'::'CDT_System'::'Logical Architecture'::'Logical Functions'::'Root Logical Function'.'Generates Reports'.'Request Report to be sent'.'inExecute Policy'); 
                            ref :>> outputs =  ('CDT_System Project'::'CDT_System'::'Logical Architecture'::'Logical Functions'::'Root Logical Function'.'Generates Reports'.'Request Report to be sent'.'FOP 1'); 
                        }  
                        action 'Generate Reports' : LogicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Operational Analysis'::'Data'::'Report'); 
                            }  
                            out port 'outParen Report' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Operational Analysis'::'Data'::'Report'); 
                            }  
                            out port 'outInstition Report' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Operational Analysis'::'Data'::'Report'); 
                            }  
                            out port 'outAthlete Report' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Operational Analysis'::'Data'::'Report'); 
                            }  
                            ref :>> inputs =  ('CDT_System Project'::'CDT_System'::'Logical Architecture'::'Logical Functions'::'Root Logical Function'.'Generates Reports'.'Generate Reports'.'FIP 1'); 
                            ref :>> outputs =  ('CDT_System Project'::'CDT_System'::'Logical Architecture'::'Logical Functions'::'Root Logical Function'.'Generates Reports'.'Generate Reports'.'outParen Report',
                            'CDT_System Project'::'CDT_System'::'Logical Architecture'::'Logical Functions'::'Root Logical Function'.'Generates Reports'.'Generate Reports'.'outInstition Report',
                            'CDT_System Project'::'CDT_System'::'Logical Architecture'::'Logical Functions'::'Root Logical Function'.'Generates Reports'.'Generate Reports'.'outAthlete Report'); 
                        }  
                        interface 'a968678a-bdee-4cc3-8a24-1cd23df515a3' : FunctionalExchange 
                            connect source ::> 'CDT_System Project'::'CDT_System'::'Logical Architecture'::'Logical Functions'::'Root Logical Function'.'Generates Reports'.'Request Report to be sent'.'FOP 1'
                            to target ::> 'CDT_System Project'::'CDT_System'::'Logical Architecture'::'Logical Functions'::'Root Logical Function'.'Generates Reports'.'Generate Reports'.'FIP 1' { 
                            attribute :>> isMulticast = false; 
                            attribute :>> kindOfRate = RateKind::Unspecified; 
                            attribute :>> isMultireceive = false; 
                            attribute :>> interfaceName = "Report Request"; 
                            ref :>> exchangedItems =  ('CDT_System Project'::'CDT_System'::'Operational Analysis'::'Data'::'Report'); 
                        }  
                        ref :>> ownedFunctions =  ('CDT_System Project'::'CDT_System'::'Logical Architecture'::'Logical Functions'::'Root Logical Function'.'Generates Reports'.'Request Report to be sent',
                        'CDT_System Project'::'CDT_System'::'Logical Architecture'::'Logical Functions'::'Root Logical Function'.'Generates Reports'.'Generate Reports'); 
                         
                        ref :>> ownedFunctionalExchanges =  ('CDT_System Project'::'CDT_System'::'Logical Architecture'::'Logical Functions'::'Root Logical Function'.'Generates Reports'.'a968678a-bdee-4cc3-8a24-1cd23df515a3'); 
                    }  
                    action 'Helmet Receives a Hit' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inActivity' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Operational Analysis'::'Data'::'Hit'); 
                             
                        }  
                        out port 'outHit' : FunctionOutputPort  { 
                            attribute :>> isControlType = false; 
                            attribute :>> ordering = ObjectNodeOrderingKind::FIFO; 
                            attribute :>> isControl = false; 
                            attribute :>> kindOfNode = ObjectNodeKind::Unspecified; 
                             
                            ref :>> outgoingExchangeItems =  ('CDT_System Project'::'CDT_System'::'Operational Analysis'::'Data'::'Hit'); 
                        }  
                        ref :>> inputs =  ('CDT_System Project'::'CDT_System'::'Logical Architecture'::'Logical Functions'::'Root Logical Function'.'Helmet Receives a Hit'.'inActivity'); 
                        ref :>> outputs =  ('CDT_System Project'::'CDT_System'::'Logical Architecture'::'Logical Functions'::'Root Logical Function'.'Helmet Receives a Hit'.'outHit'); 
                         
                    }  
                    action '653a1edf-a06b-472f-ac1d-98a95137cf8b' : LogicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                    }  
                    interface '08b345f8-96d0-4939-879f-5725053e5a0d' : FunctionalExchange 
                        connect source ::> 'CDT_System Project'::'CDT_System'::'Logical Architecture'::'Logical Functions'::'Root Logical Function'.'Aquire System'.'outSystem'
                        to target ::> 'CDT_System Project'::'CDT_System'::'Logical Architecture'::'Logical Functions'::'Root Logical Function'.'Create profiles for Athletes'.'inSystem' { 
                        attribute :>> isMulticast = false; 
                        attribute :>> kindOfRate = RateKind::Unspecified; 
                        attribute :>> isMultireceive = false; 
                        attribute :>> interfaceName = "System"; 
                         
                    }  
                    interface '36a2318b-871f-4e1b-8559-d5343e010562' : FunctionalExchange 
                        connect source ::> 'CDT_System Project'::'CDT_System'::'Logical Architecture'::'Logical Functions'::'Root Logical Function'.'Provide Data for Profile'.'outAthlete Data'
                        to target ::> 'CDT_System Project'::'CDT_System'::'Logical Architecture'::'Logical Functions'::'Root Logical Function'.'Create profiles for Athletes'.'inAthlete Data' { 
                        attribute :>> isMulticast = false; 
                        attribute :>> kindOfRate = RateKind::Unspecified; 
                        attribute :>> isMultireceive = false; 
                        attribute :>> interfaceName = "Athlete Data"; 
                         
                    }  
                    interface '34b74dfd-243a-40cc-a6a4-658f76ffe895' : FunctionalExchange 
                        connect source ::> 'CDT_System Project'::'CDT_System'::'Logical Architecture'::'Logical Functions'::'Root Logical Function'.'Create profiles for Athletes'.'outProfile Data'
                        to target ::> 'CDT_System Project'::'CDT_System'::'Logical Architecture'::'Logical Functions'::'Root Logical Function'.'Create Unique IDs'.'inProfile Data' { 
                        attribute :>> isMulticast = false; 
                        attribute :>> kindOfRate = RateKind::Unspecified; 
                        attribute :>> isMultireceive = false; 
                        attribute :>> interfaceName = "Profile Data"; 
                         
                    }  
                    interface 'de2a11d8-2409-417a-8eab-929d60e962a8' : FunctionalExchange 
                        connect source ::> 'CDT_System Project'::'CDT_System'::'Logical Architecture'::'Logical Functions'::'Root Logical Function'.'Create Unique IDs'.'outID'
                        to target ::> 'CDT_System Project'::'CDT_System'::'Logical Architecture'::'Logical Functions'::'Root Logical Function'.'Create Unique IDs for Athlete'.'Initiate ID Creation'.'inID' { 
                        attribute :>> isMulticast = false; 
                        attribute :>> kindOfRate = RateKind::Unspecified; 
                        attribute :>> isMultireceive = false; 
                        attribute :>> interfaceName = "ID"; 
                         
                    }  
                    interface '16ac8629-9665-4574-a074-9098e8fa193c' : FunctionalExchange 
                        connect source ::> 'CDT_System Project'::'CDT_System'::'Logical Architecture'::'Logical Functions'::'Root Logical Function'.'Create profiles for Athletes'.'outAthlete Profile'
                        to target ::> 'CDT_System Project'::'CDT_System'::'Logical Architecture'::'Logical Functions'::'Root Logical Function'.'Store Profile'.'Gather Profile Data'.'inAthlete Profile' { 
                        attribute :>> isMulticast = false; 
                        attribute :>> kindOfRate = RateKind::Unspecified; 
                        attribute :>> isMultireceive = false; 
                        attribute :>> interfaceName = "Athlete Profile"; 
                         
                    }  
                    interface '6f427cb0-5e63-42c7-9a23-b81b452b3e1d' : FunctionalExchange 
                        connect source ::> 'CDT_System Project'::'CDT_System'::'Logical Architecture'::'Logical Functions'::'Root Logical Function'.'Provide ID to Athlete'.'outID Card'
                        to target ::> 'CDT_System Project'::'CDT_System'::'Logical Architecture'::'Logical Functions'::'Root Logical Function'.'Recieve ID'.'inID Card' { 
                        attribute :>> isMulticast = false; 
                        attribute :>> kindOfRate = RateKind::Unspecified; 
                        attribute :>> isMultireceive = false; 
                        attribute :>> interfaceName = "ID Card"; 
                         
                    }  
                    interface 'aafcfdab-163f-41ca-8526-0c45de5d6af2' : FunctionalExchange 
                        connect source ::> 'CDT_System Project'::'CDT_System'::'Logical Architecture'::'Logical Functions'::'Root Logical Function'.'Create Unique IDs for Athlete'.'Create and Program ID'.'outID Device'
                        to target ::> 'CDT_System Project'::'CDT_System'::'Logical Architecture'::'Logical Functions'::'Root Logical Function'.'Provide ID to Athlete'.'inID Device' { 
                        attribute :>> isMulticast = false; 
                        attribute :>> kindOfRate = RateKind::Unspecified; 
                        attribute :>> isMultireceive = false; 
                        attribute :>> interfaceName = "ID Device"; 
                         
                    }  
                    interface '0bb64163-5187-4559-aa62-9bccb4369cfe' : FunctionalExchange 
                        connect source ::> 'CDT_System Project'::'CDT_System'::'Logical Architecture'::'Logical Functions'::'Root Logical Function'.'Aquire System'.'outSystem'
                        to target ::> 'CDT_System Project'::'CDT_System'::'Logical Architecture'::'Logical Functions'::'Root Logical Function'.'Assemble System Components'.'inSystem' { 
                        attribute :>> isMulticast = false; 
                        attribute :>> kindOfRate = RateKind::Unspecified; 
                        attribute :>> isMultireceive = false; 
                        attribute :>> interfaceName = "System"; 
                         
                    }  
                    interface 'e9d82fae-346e-4c0b-9a92-dcc49d7a2bbb' : FunctionalExchange 
                        connect source ::> 'CDT_System Project'::'CDT_System'::'Logical Architecture'::'Logical Functions'::'Root Logical Function'.'Provide access to helmut mounting'.'outhelmut mounting'
                        to target ::> 'CDT_System Project'::'CDT_System'::'Logical Architecture'::'Logical Functions'::'Root Logical Function'.'Assemble System Components'.'inhelmut mounting' { 
                        attribute :>> isMulticast = false; 
                        attribute :>> kindOfRate = RateKind::Unspecified; 
                        attribute :>> isMultireceive = false; 
                        attribute :>> interfaceName = "helmet mounting"; 
                         
                    }  
                    interface 'b4eab17b-ed8d-4af7-869d-998f966d1bc2' : FunctionalExchange 
                        connect source ::> 'CDT_System Project'::'CDT_System'::'Logical Architecture'::'Logical Functions'::'Root Logical Function'.'Recieve ID'.'outAthlete ID'
                        to target ::> 'CDT_System Project'::'CDT_System'::'Logical Architecture'::'Logical Functions'::'Root Logical Function'.'Enable Secure Collection'.'inAthlete ID' { 
                        attribute :>> isMulticast = false; 
                        attribute :>> kindOfRate = RateKind::Unspecified; 
                        attribute :>> isMultireceive = false; 
                        attribute :>> interfaceName = "Athlete ID"; 
                         
                    }  
                    interface '55e3ecb0-03f8-41d9-a02c-abb32c6cfe0c' : FunctionalExchange 
                        connect source ::> 'CDT_System Project'::'CDT_System'::'Logical Architecture'::'Logical Functions'::'Root Logical Function'.'Provide access to sensing device mounting'.'outsensor mounting'
                        to target ::> 'CDT_System Project'::'CDT_System'::'Logical Architecture'::'Logical Functions'::'Root Logical Function'.'Assemble System Components'.'insensor mounting' { 
                        attribute :>> isMulticast = false; 
                        attribute :>> kindOfRate = RateKind::Unspecified; 
                        attribute :>> isMultireceive = false; 
                        attribute :>> interfaceName = "sensor mounting"; 
                         
                    }  
                    interface '813cc0b2-5aca-4246-a3d7-66055075ecd6' : FunctionalExchange 
                        connect source ::> 'CDT_System Project'::'CDT_System'::'Logical Architecture'::'Logical Functions'::'Root Logical Function'.'Assemble System Components'.'outAssembled System'
                        to target ::> 'CDT_System Project'::'CDT_System'::'Logical Architecture'::'Logical Functions'::'Root Logical Function'.'Prep the device for use'.'inAssembled System' { 
                        attribute :>> isMulticast = false; 
                        attribute :>> kindOfRate = RateKind::Unspecified; 
                        attribute :>> isMultireceive = false; 
                        attribute :>> interfaceName = "Assembled System"; 
                         
                    }  
                    interface 'b8bd28fc-460e-46d1-a8a0-3cbe9832ab95' : FunctionalExchange 
                        connect source ::> 'CDT_System Project'::'CDT_System'::'Logical Architecture'::'Logical Functions'::'Root Logical Function'.'Recieve ID'.'outID'
                        to target ::> 'CDT_System Project'::'CDT_System'::'Logical Architecture'::'Logical Functions'::'Root Logical Function'.'Insert ID into Sensing Device'.'inID' { 
                        attribute :>> isMulticast = false; 
                        attribute :>> kindOfRate = RateKind::Unspecified; 
                        attribute :>> isMultireceive = false; 
                        attribute :>> interfaceName = "ID"; 
                         
                    }  
                    interface '00d758e5-8a75-4f64-b22e-78cc1cadaeb8' : FunctionalExchange 
                        connect source ::> 'CDT_System Project'::'CDT_System'::'Logical Architecture'::'Logical Functions'::'Root Logical Function'.'Insert ID into Sensing Device'.'outID'
                        to target ::> 'CDT_System Project'::'CDT_System'::'Logical Architecture'::'Logical Functions'::'Root Logical Function'.'Recieve ID'.'inID' { 
                        attribute :>> isMulticast = false; 
                        attribute :>> kindOfRate = RateKind::Unspecified; 
                        attribute :>> isMultireceive = false; 
                        attribute :>> interfaceName = "ID"; 
                         
                    }  
                    interface '56e3f648-295a-488f-b3d0-b6c6fd35f619' : FunctionalExchange 
                        connect source ::> 'CDT_System Project'::'CDT_System'::'Logical Architecture'::'Logical Functions'::'Root Logical Function'.'Receive Athlete '.'outHelmut Motion'
                        to target ::> 'CDT_System Project'::'CDT_System'::'Logical Architecture'::'Logical Functions'::'Root Logical Function'.'Enable Monitoring'.'Enable Monitoring'.'inHelmut Motion' { 
                        attribute :>> isMulticast = false; 
                        attribute :>> kindOfRate = RateKind::Unspecified; 
                        attribute :>> isMultireceive = false; 
                        attribute :>> interfaceName = "Helmet Motion"; 
                         
                    }  
                    interface '4e51009a-8ee1-4cd3-87bb-2a6ea590ffad' : FunctionalExchange 
                        connect source ::> 'CDT_System Project'::'CDT_System'::'Logical Architecture'::'Logical Functions'::'Root Logical Function'.'Place on Helmut'.'outHead '
                        to target ::> 'CDT_System Project'::'CDT_System'::'Logical Architecture'::'Logical Functions'::'Root Logical Function'.'Receive Athlete '.'inHead ' { 
                        attribute :>> isMulticast = false; 
                        attribute :>> kindOfRate = RateKind::Unspecified; 
                        attribute :>> isMultireceive = false; 
                        attribute :>> interfaceName = "Head "; 
                         
                    }  
                    interface '71992433-b730-4c78-b2c6-634c4f622ff2' : FunctionalExchange 
                        connect source ::> 'CDT_System Project'::'CDT_System'::'Logical Architecture'::'Logical Functions'::'Root Logical Function'.'Data is Retrieved'.'Intitate Data Retrieval'.'outRecorded Data'
                        to target ::> 'CDT_System Project'::'CDT_System'::'Logical Architecture'::'Logical Functions'::'Root Logical Function'.'Data stored'.'Data Stored'.'inRecorded Data' { 
                        attribute :>> isMulticast = false; 
                        attribute :>> kindOfRate = RateKind::Unspecified; 
                        attribute :>> isMultireceive = false; 
                        attribute :>> interfaceName = "Recorded Data"; 
                         
                        ref :>> exchangedItems =  ('CDT_System Project'::'CDT_System'::'Operational Analysis'::'Data'::'Concussion Data'); 
                    }  
                    interface '01f8b08a-4640-420b-8d83-dba3864e5805' : FunctionalExchange 
                        connect source ::> 'CDT_System Project'::'CDT_System'::'Logical Architecture'::'Logical Functions'::'Root Logical Function'.'Data stored'.'Data is Presented'.'outStored Data '
                        to target ::> 'CDT_System Project'::'CDT_System'::'Logical Architecture'::'Logical Functions'::'Root Logical Function'.'Data can be reviewed'.'inStored Data ' { 
                        attribute :>> isMulticast = false; 
                        attribute :>> kindOfRate = RateKind::Unspecified; 
                        attribute :>> isMultireceive = false; 
                        attribute :>> interfaceName = "Stored Data "; 
                         
                        ref :>> exchangedItems =  ('CDT_System Project'::'CDT_System'::'Operational Analysis'::'Data'::'Concussion Data'); 
                    }  
                    interface '2f84f25a-c0c3-4273-bddd-f328cfa6ebd4' : FunctionalExchange 
                        connect source ::> 'CDT_System Project'::'CDT_System'::'Logical Architecture'::'Logical Functions'::'Root Logical Function'.'Data can be reviewed'.'outInteraction 26'
                        to target ::> 'CDT_System Project'::'CDT_System'::'Logical Architecture'::'Logical Functions'::'Root Logical Function'.'Executes Policies'.'inInteraction 26' { 
                        attribute :>> isMulticast = false; 
                        attribute :>> kindOfRate = RateKind::Unspecified; 
                        attribute :>> isMultireceive = false; 
                        attribute :>> interfaceName = "Interaction 26"; 
                         
                    }  
                    interface '62df0638-2fc0-4bc4-9c70-2eeb40eb41f5' : FunctionalExchange 
                        connect source ::> 'CDT_System Project'::'CDT_System'::'Logical Architecture'::'Logical Functions'::'Root Logical Function'.'Aquire System'.'outSystem '
                        to target ::> 'CDT_System Project'::'CDT_System'::'Logical Architecture'::'Logical Functions'::'Root Logical Function'.'Established Concussion Policy'.'inSystem ' { 
                        attribute :>> isMulticast = false; 
                        attribute :>> kindOfRate = RateKind::Unspecified; 
                        attribute :>> isMultireceive = false; 
                        attribute :>> interfaceName = "System "; 
                         
                    }  
                    interface 'a02cc65e-95fe-4a14-9ddc-e85e3ac99c25' : FunctionalExchange 
                        connect source ::> 'CDT_System Project'::'CDT_System'::'Logical Architecture'::'Logical Functions'::'Root Logical Function'.'Established Concussion Policy'.'outConcussion Policy'
                        to target ::> 'CDT_System Project'::'CDT_System'::'Logical Architecture'::'Logical Functions'::'Root Logical Function'.'Trainer Recieves Concussion Alert'.'inConcussion Policy' { 
                        attribute :>> isMulticast = false; 
                        attribute :>> kindOfRate = RateKind::Unspecified; 
                        attribute :>> isMultireceive = false; 
                        attribute :>> interfaceName = "Concussion Policy"; 
                         
                    }  
                    interface 'dbbb6ead-6656-4c2d-b504-bbe6fc344884' : FunctionalExchange 
                        connect source ::> 'CDT_System Project'::'CDT_System'::'Logical Architecture'::'Logical Functions'::'Root Logical Function'.'Provide ID Information'.'outDevice ID '
                        to target ::> 'CDT_System Project'::'CDT_System'::'Logical Architecture'::'Logical Functions'::'Root Logical Function'.'Enable Secure Collection'.'inDevice ID ' { 
                        attribute :>> isMulticast = false; 
                        attribute :>> kindOfRate = RateKind::Unspecified; 
                        attribute :>> isMultireceive = false; 
                        attribute :>> interfaceName = "Device ID "; 
                         
                    }  
                    interface '4776ac92-de15-48ad-a25f-efac32182fe7' : FunctionalExchange 
                        connect source ::> 'CDT_System Project'::'CDT_System'::'Logical Architecture'::'Logical Functions'::'Root Logical Function'.'Executes Policies'.'outExecute Policy'
                        to target ::> 'CDT_System Project'::'CDT_System'::'Logical Architecture'::'Logical Functions'::'Root Logical Function'.'Generates Reports'.'Request Report to be sent'.'inExecute Policy' { 
                        attribute :>> isMulticast = false; 
                        attribute :>> kindOfRate = RateKind::Unspecified; 
                        attribute :>> isMultireceive = false; 
                        attribute :>> interfaceName = "Execute Policy"; 
                         
                        ref :>> exchangedItems =  ('CDT_System Project'::'CDT_System'::'Operational Analysis'::'Data'::'Policy'); 
                    }  
                    interface '614f2cf6-af23-4751-b457-0ab203481315' : FunctionalExchange 
                        connect source ::> 'CDT_System Project'::'CDT_System'::'Logical Architecture'::'Logical Functions'::'Root Logical Function'.'Trainer Recieves Concussion Alert'.'outAlert'
                        to target ::> 'CDT_System Project'::'CDT_System'::'Logical Architecture'::'Logical Functions'::'Root Logical Function'.'Yield to Evaluation'.'inAlert' { 
                        attribute :>> isMulticast = false; 
                        attribute :>> kindOfRate = RateKind::Unspecified; 
                        attribute :>> isMultireceive = false; 
                        attribute :>> interfaceName = "Alert"; 
                         
                    }  
                    interface '635ccece-c152-41cc-995f-6716650aa8fa' : FunctionalExchange 
                        connect source ::> 'CDT_System Project'::'CDT_System'::'Logical Architecture'::'Logical Functions'::'Root Logical Function'.'Generates Reports'.'Generate Reports'.'outAthlete Report'
                        to target ::> 'CDT_System Project'::'CDT_System'::'Logical Architecture'::'Logical Functions'::'Root Logical Function'.'Report Received'.'inAthlete Report' { 
                        attribute :>> isMulticast = false; 
                        attribute :>> kindOfRate = RateKind::Unspecified; 
                        attribute :>> isMultireceive = false; 
                        attribute :>> interfaceName = "Athlete Report"; 
                         
                        ref :>> exchangedItems =  ('CDT_System Project'::'CDT_System'::'Operational Analysis'::'Data'::'Report'); 
                    }  
                    interface 'de8f7c10-fd24-4d5f-ad53-43652989cb4c' : FunctionalExchange 
                        connect source ::> 'CDT_System Project'::'CDT_System'::'Logical Architecture'::'Logical Functions'::'Root Logical Function'.'Enable Secure Collection'.'outSensor Ready'
                        to target ::> 'CDT_System Project'::'CDT_System'::'Logical Architecture'::'Logical Functions'::'Root Logical Function'.'Enable Monitoring'.'Enable Monitoring'.'inSensor Ready' { 
                        attribute :>> isMulticast = false; 
                        attribute :>> kindOfRate = RateKind::Unspecified; 
                        attribute :>> isMultireceive = false; 
                        attribute :>> interfaceName = "Sensor Ready"; 
                         
                    }  
                    interface '1006a2a3-51b8-4014-b186-94587fe4de06' : FunctionalExchange 
                        connect source ::> 'CDT_System Project'::'CDT_System'::'Logical Architecture'::'Logical Functions'::'Root Logical Function'.'Enable Monitoring'.'Enable Indicated'.'outEnable Signal'
                        to target ::> 'CDT_System Project'::'CDT_System'::'Logical Architecture'::'Logical Functions'::'Root Logical Function'.'Recieve Enabled Signal from Athelete Helmut'.'inEnable Signal' { 
                        attribute :>> isMulticast = false; 
                        attribute :>> kindOfRate = RateKind::Unspecified; 
                        attribute :>> isMultireceive = false; 
                        attribute :>> interfaceName = "Enable Signal"; 
                         
                    }  
                    interface 'ca27fda2-31e3-46f1-8961-666dd0d43912' : FunctionalExchange 
                        connect source ::> 'CDT_System Project'::'CDT_System'::'Logical Architecture'::'Logical Functions'::'Root Logical Function'.'Insert ID into Sensing Device'.'outReady to put on Helmut'
                        to target ::> 'CDT_System Project'::'CDT_System'::'Logical Architecture'::'Logical Functions'::'Root Logical Function'.'Place on Helmut'.'inReady to put on Helmut' { 
                        attribute :>> isMulticast = false; 
                        attribute :>> kindOfRate = RateKind::Unspecified; 
                        attribute :>> isMultireceive = false; 
                        attribute :>> interfaceName = "Ready to put on Helmet"; 
                         
                    }  
                    interface '7c65fcce-2e69-4088-8879-09f2ae47a639' : FunctionalExchange 
                        connect source ::> 'CDT_System Project'::'CDT_System'::'Logical Architecture'::'Logical Functions'::'Root Logical Function'.'Generates Reports'.'Generate Reports'.'outInstition Report'
                        to target ::> 'CDT_System Project'::'CDT_System'::'Logical Architecture'::'Logical Functions'::'Root Logical Function'.'Report Received'.'inInstition Report' { 
                        attribute :>> isMulticast = false; 
                        attribute :>> kindOfRate = RateKind::Unspecified; 
                        attribute :>> isMultireceive = false; 
                        attribute :>> interfaceName = "Instition Report"; 
                         
                        ref :>> exchangedItems =  ('CDT_System Project'::'CDT_System'::'Operational Analysis'::'Data'::'Report'); 
                    }  
                    interface '38922abf-b0ac-4ded-8226-7b753f82ecd3' : FunctionalExchange 
                        connect source ::> 'CDT_System Project'::'CDT_System'::'Logical Architecture'::'Logical Functions'::'Root Logical Function'.'Generates Reports'.'Generate Reports'.'outParen Report'
                        to target ::> 'CDT_System Project'::'CDT_System'::'Logical Architecture'::'Logical Functions'::'Root Logical Function'.'Report received'.'inParen Report' { 
                        attribute :>> isMulticast = false; 
                        attribute :>> kindOfRate = RateKind::Unspecified; 
                        attribute :>> isMultireceive = false; 
                        attribute :>> interfaceName = "Paren Report"; 
                         
                        ref :>> exchangedItems =  ('CDT_System Project'::'CDT_System'::'Operational Analysis'::'Data'::'Report'); 
                    }  
                    interface '2e9251b0-4ed5-4638-ac5f-70e316e6fd80' : FunctionalExchange 
                        connect source ::> 'CDT_System Project'::'CDT_System'::'Logical Architecture'::'Logical Functions'::'Root Logical Function'.'Yield to Evaluation'.'outEvaluation'
                        to target ::> 'CDT_System Project'::'CDT_System'::'Logical Architecture'::'Logical Functions'::'Root Logical Function'.'Data is Retrieved'.'Intitate Data Retrieval'.'inEvaluation' { 
                        attribute :>> isMulticast = false; 
                        attribute :>> kindOfRate = RateKind::Unspecified; 
                        attribute :>> isMultireceive = false; 
                        attribute :>> interfaceName = "Evaluation"; 
                         
                    }  
                    interface 'aa8aeda1-33ce-4fc7-be1b-a304cb2015fe' : FunctionalExchange 
                        connect source ::> 'CDT_System Project'::'CDT_System'::'Logical Architecture'::'Logical Functions'::'Root Logical Function'.'Device alerts possible Concussion'.'Alert the Training'.'outConcussion Alert to Trainer'
                        to target ::> 'CDT_System Project'::'CDT_System'::'Logical Architecture'::'Logical Functions'::'Root Logical Function'.'Trainer Recieves Concussion Alert'.'inConcussion Alert to Trainer' { 
                        attribute :>> isMulticast = false; 
                        attribute :>> kindOfRate = RateKind::Unspecified; 
                        attribute :>> isMultireceive = false; 
                        attribute :>> interfaceName = "Concussion Alert to Trainer"; 
                         
                        ref :>> exchangedItems =  ('CDT_System Project'::'CDT_System'::'Operational Analysis'::'Data'::'Alert'); 
                    }  
                    interface '033e3152-51b3-45d7-a9a1-aae2f3decad1' : FunctionalExchange 
                        connect source ::> 'CDT_System Project'::'CDT_System'::'Logical Architecture'::'Logical Functions'::'Root Logical Function'.'Athlete Particpates in Activity'.'outActivity'
                        to target ::> 'CDT_System Project'::'CDT_System'::'Logical Architecture'::'Logical Functions'::'Root Logical Function'.'Helmet Receives a Hit'.'inActivity' { 
                        attribute :>> isMulticast = false; 
                        attribute :>> kindOfRate = RateKind::Unspecified; 
                        attribute :>> isMultireceive = false; 
                        attribute :>> interfaceName = "Activity"; 
                         
                        ref :>> exchangedItems =  ('CDT_System Project'::'CDT_System'::'Operational Analysis'::'Data'::'Hit'); 
                    }  
                    interface '68e7ee56-30a5-4c17-8bfb-5309173b9a78' : FunctionalExchange 
                        connect source ::> 'CDT_System Project'::'CDT_System'::'Logical Architecture'::'Logical Functions'::'Root Logical Function'.'Helmet Receives a Hit'.'outHit'
                        to target ::> 'CDT_System Project'::'CDT_System'::'Logical Architecture'::'Logical Functions'::'Root Logical Function'.'Device records Hit'.'inHit' { 
                        attribute :>> isMulticast = false; 
                        attribute :>> kindOfRate = RateKind::Unspecified; 
                        attribute :>> isMultireceive = false; 
                        attribute :>> interfaceName = "Hit"; 
                         
                        ref :>> exchangedItems =  ('CDT_System Project'::'CDT_System'::'Operational Analysis'::'Data'::'Hit'); 
                    }  
                    interface '97bdedf8-82ae-456e-8aa0-5a2822061c06' : FunctionalExchange 
                        connect source ::> 'CDT_System Project'::'CDT_System'::'Logical Architecture'::'Logical Functions'::'Root Logical Function'.'Device records Hit'.'outConcussion'
                        to target ::> 'CDT_System Project'::'CDT_System'::'Logical Architecture'::'Logical Functions'::'Root Logical Function'.'Device alerts possible Concussion'.'Send message'.'inConcussion' { 
                        attribute :>> isMulticast = false; 
                        attribute :>> kindOfRate = RateKind::Unspecified; 
                        attribute :>> isMultireceive = false; 
                        attribute :>> interfaceName = "Concussion"; 
                         
                        ref :>> exchangedItems =  ('CDT_System Project'::'CDT_System'::'Operational Analysis'::'Data'::'Alert'); 
                    }  
                    interface '51513826-9e5b-41a3-8a8a-e83bd29f289a' : FunctionalExchange 
                        connect source ::> 'CDT_System Project'::'CDT_System'::'Logical Architecture'::'Logical Functions'::'Root Logical Function'.'Device records Hit'.'outStored Data'
                        to target ::> 'CDT_System Project'::'CDT_System'::'Logical Architecture'::'Logical Functions'::'Root Logical Function'.'Data is Retrieved'.'Provide Hit Data'.'inStored Data' { 
                        attribute :>> isMulticast = false; 
                        attribute :>> kindOfRate = RateKind::Unspecified; 
                        attribute :>> isMultireceive = false; 
                        attribute :>> interfaceName = "Stored Data"; 
                         
                        ref :>> exchangedItems =  ('CDT_System Project'::'CDT_System'::'Operational Analysis'::'Data'::'Concussion Data'); 
                    }  
                    interface '141f7a3c-ac31-4dcb-97f0-030743f4cf14' : FunctionalExchange 
                        connect source ::> 'CDT_System Project'::'CDT_System'::'Logical Architecture'::'Logical Functions'::'Root Logical Function'.'Trainer Recieves Concussion Alert'.'FOP 2'
                        to target ::> 'CDT_System Project'::'CDT_System'::'Logical Architecture'::'Logical Functions'::'Root Logical Function'.'Data is Retrieved'.'Intitate Data Retrieval'.'FIP 1' { 
                        attribute :>> isMulticast = false; 
                        attribute :>> kindOfRate = RateKind::Unspecified; 
                        attribute :>> isMultireceive = false; 
                        attribute :>> interfaceName = "Retrieve"; 
                    }  
                    interface '844adaef-76be-4b7b-9fd1-ba948c8ad5c3' : FunctionalExchange 
                        connect source ::> 'CDT_System Project'::'CDT_System'::'Logical Architecture'::'Logical Functions'::'Root Logical Function'.'Device alerts possible Concussion'.'Alert the Training'.'FOP 2'
                        to target ::> 'CDT_System Project'::'CDT_System'::'Logical Architecture'::'Logical Functions'::'Root Logical Function'.'Data is Retrieved'.'Intitate Data Retrieval'.'FIP 2' { 
                        attribute :>> isMulticast = false; 
                        attribute :>> kindOfRate = RateKind::Unspecified; 
                        attribute :>> isMultireceive = false; 
                        attribute :>> interfaceName = "Player ID"; 
                    }  
                    interface '2da9d91f-1db5-4020-a709-32ac5622aa79' : FunctionalExchange 
                        connect source ::> 'CDT_System Project'::'CDT_System'::'Logical Architecture'::'Logical Functions'::'Root Logical Function'.'Store Profile'.'Store Profile'.'FOP 1'
                        to target ::> 'CDT_System Project'::'CDT_System'::'Logical Architecture'::'Logical Functions'::'Root Logical Function'.'Create Unique IDs for Athlete'.'Create ID'.'FIP 2' { 
                        attribute :>> isMulticast = false; 
                        attribute :>> kindOfRate = RateKind::Unspecified; 
                        attribute :>> isMultireceive = false; 
                        attribute :>> interfaceName = "Profile Data"; 
                    }  
                     
                    ref :>> ownedFunctions =  ('CDT_System Project'::'CDT_System'::'Logical Architecture'::'Logical Functions'::'Root Logical Function'.'Aquire System',
                    'CDT_System Project'::'CDT_System'::'Logical Architecture'::'Logical Functions'::'Root Logical Function'.'Create profiles for Athletes',
                    'CDT_System Project'::'CDT_System'::'Logical Architecture'::'Logical Functions'::'Root Logical Function'.'Create Unique IDs for Athlete',
                    'CDT_System Project'::'CDT_System'::'Logical Architecture'::'Logical Functions'::'Root Logical Function'.'Provide Data for Profile',
                    'CDT_System Project'::'CDT_System'::'Logical Architecture'::'Logical Functions'::'Root Logical Function'.'Recieve ID',
                    'CDT_System Project'::'CDT_System'::'Logical Architecture'::'Logical Functions'::'Root Logical Function'.'Store Profile',
                    'CDT_System Project'::'CDT_System'::'Logical Architecture'::'Logical Functions'::'Root Logical Function'.'Create Unique IDs',
                    'CDT_System Project'::'CDT_System'::'Logical Architecture'::'Logical Functions'::'Root Logical Function'.'Provide ID to Athlete',
                    'CDT_System Project'::'CDT_System'::'Logical Architecture'::'Logical Functions'::'Root Logical Function'.'Assemble System Components',
                    'CDT_System Project'::'CDT_System'::'Logical Architecture'::'Logical Functions'::'Root Logical Function'.'Provide access to helmut mounting',
                    'CDT_System Project'::'CDT_System'::'Logical Architecture'::'Logical Functions'::'Root Logical Function'.'Provide access to sensing device mounting',
                    'CDT_System Project'::'CDT_System'::'Logical Architecture'::'Logical Functions'::'Root Logical Function'.'Prep the device for use',
                    'CDT_System Project'::'CDT_System'::'Logical Architecture'::'Logical Functions'::'Root Logical Function'.'Insert ID into Sensing Device',
                    'CDT_System Project'::'CDT_System'::'Logical Architecture'::'Logical Functions'::'Root Logical Function'.'Recieve ID',
                    'CDT_System Project'::'CDT_System'::'Logical Architecture'::'Logical Functions'::'Root Logical Function'.'Device alerts possible Concussion',
                    'CDT_System Project'::'CDT_System'::'Logical Architecture'::'Logical Functions'::'Root Logical Function'.'Trainer Recieves Concussion Alert',
                    'CDT_System Project'::'CDT_System'::'Logical Architecture'::'Logical Functions'::'Root Logical Function'.'Device records Hit',
                    'CDT_System Project'::'CDT_System'::'Logical Architecture'::'Logical Functions'::'Root Logical Function'.'Enable Secure Collection',
                    'CDT_System Project'::'CDT_System'::'Logical Architecture'::'Logical Functions'::'Root Logical Function'.'Place on Helmut',
                    'CDT_System Project'::'CDT_System'::'Logical Architecture'::'Logical Functions'::'Root Logical Function'.'Device',
                    'CDT_System Project'::'CDT_System'::'Logical Architecture'::'Logical Functions'::'Root Logical Function'.'Provide ID Information',
                    'CDT_System Project'::'CDT_System'::'Logical Architecture'::'Logical Functions'::'Root Logical Function'.'Athlete Particpates in Activity',
                    'CDT_System Project'::'CDT_System'::'Logical Architecture'::'Logical Functions'::'Root Logical Function'.'Yield to Evaluation',
                    'CDT_System Project'::'CDT_System'::'Logical Architecture'::'Logical Functions'::'Root Logical Function'.'Receive Athlete ',
                    'CDT_System Project'::'CDT_System'::'Logical Architecture'::'Logical Functions'::'Root Logical Function'.'Data is Retrieved',
                    'CDT_System Project'::'CDT_System'::'Logical Architecture'::'Logical Functions'::'Root Logical Function'.'Enable Monitoring',
                    'CDT_System Project'::'CDT_System'::'Logical Architecture'::'Logical Functions'::'Root Logical Function'.'Recieve Enabled Signal from Athelete Helmut',
                    'CDT_System Project'::'CDT_System'::'Logical Architecture'::'Logical Functions'::'Root Logical Function'.'Data stored',
                    'CDT_System Project'::'CDT_System'::'Logical Architecture'::'Logical Functions'::'Root Logical Function'.'Data can be reviewed',
                    'CDT_System Project'::'CDT_System'::'Logical Architecture'::'Logical Functions'::'Root Logical Function'.'Report Received',
                    'CDT_System Project'::'CDT_System'::'Logical Architecture'::'Logical Functions'::'Root Logical Function'.'Report Received',
                    'CDT_System Project'::'CDT_System'::'Logical Architecture'::'Logical Functions'::'Root Logical Function'.'Report received',
                    'CDT_System Project'::'CDT_System'::'Logical Architecture'::'Logical Functions'::'Root Logical Function'.'Executes Policies',
                    'CDT_System Project'::'CDT_System'::'Logical Architecture'::'Logical Functions'::'Root Logical Function'.'Established Concussion Policy',
                    'CDT_System Project'::'CDT_System'::'Logical Architecture'::'Logical Functions'::'Root Logical Function'.'Generates Reports',
                    'CDT_System Project'::'CDT_System'::'Logical Architecture'::'Logical Functions'::'Root Logical Function'.'Helmet Receives a Hit',
                    'CDT_System Project'::'CDT_System'::'Logical Architecture'::'Logical Functions'::'Root Logical Function'.'653a1edf-a06b-472f-ac1d-98a95137cf8b'); 
                     
                    ref :>> ownedFunctionalExchanges =  ('CDT_System Project'::'CDT_System'::'Logical Architecture'::'Logical Functions'::'Root Logical Function'.'08b345f8-96d0-4939-879f-5725053e5a0d',
                    'CDT_System Project'::'CDT_System'::'Logical Architecture'::'Logical Functions'::'Root Logical Function'.'36a2318b-871f-4e1b-8559-d5343e010562',
                    'CDT_System Project'::'CDT_System'::'Logical Architecture'::'Logical Functions'::'Root Logical Function'.'34b74dfd-243a-40cc-a6a4-658f76ffe895',
                    'CDT_System Project'::'CDT_System'::'Logical Architecture'::'Logical Functions'::'Root Logical Function'.'de2a11d8-2409-417a-8eab-929d60e962a8',
                    'CDT_System Project'::'CDT_System'::'Logical Architecture'::'Logical Functions'::'Root Logical Function'.'16ac8629-9665-4574-a074-9098e8fa193c',
                    'CDT_System Project'::'CDT_System'::'Logical Architecture'::'Logical Functions'::'Root Logical Function'.'6f427cb0-5e63-42c7-9a23-b81b452b3e1d',
                    'CDT_System Project'::'CDT_System'::'Logical Architecture'::'Logical Functions'::'Root Logical Function'.'aafcfdab-163f-41ca-8526-0c45de5d6af2',
                    'CDT_System Project'::'CDT_System'::'Logical Architecture'::'Logical Functions'::'Root Logical Function'.'0bb64163-5187-4559-aa62-9bccb4369cfe',
                    'CDT_System Project'::'CDT_System'::'Logical Architecture'::'Logical Functions'::'Root Logical Function'.'e9d82fae-346e-4c0b-9a92-dcc49d7a2bbb',
                    'CDT_System Project'::'CDT_System'::'Logical Architecture'::'Logical Functions'::'Root Logical Function'.'b4eab17b-ed8d-4af7-869d-998f966d1bc2',
                    'CDT_System Project'::'CDT_System'::'Logical Architecture'::'Logical Functions'::'Root Logical Function'.'55e3ecb0-03f8-41d9-a02c-abb32c6cfe0c',
                    'CDT_System Project'::'CDT_System'::'Logical Architecture'::'Logical Functions'::'Root Logical Function'.'813cc0b2-5aca-4246-a3d7-66055075ecd6',
                    'CDT_System Project'::'CDT_System'::'Logical Architecture'::'Logical Functions'::'Root Logical Function'.'b8bd28fc-460e-46d1-a8a0-3cbe9832ab95',
                    'CDT_System Project'::'CDT_System'::'Logical Architecture'::'Logical Functions'::'Root Logical Function'.'00d758e5-8a75-4f64-b22e-78cc1cadaeb8',
                    'CDT_System Project'::'CDT_System'::'Logical Architecture'::'Logical Functions'::'Root Logical Function'.'56e3f648-295a-488f-b3d0-b6c6fd35f619',
                    'CDT_System Project'::'CDT_System'::'Logical Architecture'::'Logical Functions'::'Root Logical Function'.'4e51009a-8ee1-4cd3-87bb-2a6ea590ffad',
                    'CDT_System Project'::'CDT_System'::'Logical Architecture'::'Logical Functions'::'Root Logical Function'.'71992433-b730-4c78-b2c6-634c4f622ff2',
                    'CDT_System Project'::'CDT_System'::'Logical Architecture'::'Logical Functions'::'Root Logical Function'.'01f8b08a-4640-420b-8d83-dba3864e5805',
                    'CDT_System Project'::'CDT_System'::'Logical Architecture'::'Logical Functions'::'Root Logical Function'.'2f84f25a-c0c3-4273-bddd-f328cfa6ebd4',
                    'CDT_System Project'::'CDT_System'::'Logical Architecture'::'Logical Functions'::'Root Logical Function'.'62df0638-2fc0-4bc4-9c70-2eeb40eb41f5',
                    'CDT_System Project'::'CDT_System'::'Logical Architecture'::'Logical Functions'::'Root Logical Function'.'a02cc65e-95fe-4a14-9ddc-e85e3ac99c25',
                    'CDT_System Project'::'CDT_System'::'Logical Architecture'::'Logical Functions'::'Root Logical Function'.'dbbb6ead-6656-4c2d-b504-bbe6fc344884',
                    'CDT_System Project'::'CDT_System'::'Logical Architecture'::'Logical Functions'::'Root Logical Function'.'4776ac92-de15-48ad-a25f-efac32182fe7',
                    'CDT_System Project'::'CDT_System'::'Logical Architecture'::'Logical Functions'::'Root Logical Function'.'614f2cf6-af23-4751-b457-0ab203481315',
                    'CDT_System Project'::'CDT_System'::'Logical Architecture'::'Logical Functions'::'Root Logical Function'.'635ccece-c152-41cc-995f-6716650aa8fa',
                    'CDT_System Project'::'CDT_System'::'Logical Architecture'::'Logical Functions'::'Root Logical Function'.'de8f7c10-fd24-4d5f-ad53-43652989cb4c',
                    'CDT_System Project'::'CDT_System'::'Logical Architecture'::'Logical Functions'::'Root Logical Function'.'1006a2a3-51b8-4014-b186-94587fe4de06',
                    'CDT_System Project'::'CDT_System'::'Logical Architecture'::'Logical Functions'::'Root Logical Function'.'ca27fda2-31e3-46f1-8961-666dd0d43912',
                    'CDT_System Project'::'CDT_System'::'Logical Architecture'::'Logical Functions'::'Root Logical Function'.'7c65fcce-2e69-4088-8879-09f2ae47a639',
                    'CDT_System Project'::'CDT_System'::'Logical Architecture'::'Logical Functions'::'Root Logical Function'.'38922abf-b0ac-4ded-8226-7b753f82ecd3',
                    'CDT_System Project'::'CDT_System'::'Logical Architecture'::'Logical Functions'::'Root Logical Function'.'2e9251b0-4ed5-4638-ac5f-70e316e6fd80',
                    'CDT_System Project'::'CDT_System'::'Logical Architecture'::'Logical Functions'::'Root Logical Function'.'aa8aeda1-33ce-4fc7-be1b-a304cb2015fe',
                    'CDT_System Project'::'CDT_System'::'Logical Architecture'::'Logical Functions'::'Root Logical Function'.'033e3152-51b3-45d7-a9a1-aae2f3decad1',
                    'CDT_System Project'::'CDT_System'::'Logical Architecture'::'Logical Functions'::'Root Logical Function'.'68e7ee56-30a5-4c17-8bfb-5309173b9a78',
                    'CDT_System Project'::'CDT_System'::'Logical Architecture'::'Logical Functions'::'Root Logical Function'.'97bdedf8-82ae-456e-8aa0-5a2822061c06',
                    'CDT_System Project'::'CDT_System'::'Logical Architecture'::'Logical Functions'::'Root Logical Function'.'51513826-9e5b-41a3-8a8a-e83bd29f289a',
                    'CDT_System Project'::'CDT_System'::'Logical Architecture'::'Logical Functions'::'Root Logical Function'.'141f7a3c-ac31-4dcb-97f0-030743f4cf14',
                    'CDT_System Project'::'CDT_System'::'Logical Architecture'::'Logical Functions'::'Root Logical Function'.'844adaef-76be-4b7b-9fd1-ba948c8ad5c3',
                    'CDT_System Project'::'CDT_System'::'Logical Architecture'::'Logical Functions'::'Root Logical Function'.'2da9d91f-1db5-4020-a709-32ac5622aa79'); 
                }  
            } 
            package  'Interfaces' {
                @PackageMeta {
                    type = "InterfacePkg";
                } 
                item 'Hit' : InterfaceItem  { 
                    attribute :>> isStructural = true; 
                    attribute :>> isAbstract = false; 
                    attribute :>> isFinal = false; 
                    allocation '5a6abe49-8ea8-4244-8bd2-c7c665d84812' : ExchangeItemAllocation
                        allocate allocatedItem ::> 'CDT_System Project'::'CDT_System'::'Operational Analysis'::'Data'::'Hit'
                        to allocatingInterface ::> 'CDT_System Project'::'CDT_System'::'Logical Architecture'::'Interfaces'::'Hit'; 
                     
                    ref :>> ownedExchangeItemAllocations =  ('CDT_System Project'::'CDT_System'::'Logical Architecture'::'Interfaces'::'Hit'.'5a6abe49-8ea8-4244-8bd2-c7c665d84812'); 
                     
                }  
                item 'Alert' : InterfaceItem  { 
                    attribute :>> isStructural = true; 
                    attribute :>> isAbstract = false; 
                    attribute :>> isFinal = false; 
                    allocation 'ea25187d-22ba-4c73-bb79-7e36343a8aa1' : ExchangeItemAllocation
                        allocate allocatedItem ::> 'CDT_System Project'::'CDT_System'::'Operational Analysis'::'Data'::'Alert'
                        to allocatingInterface ::> 'CDT_System Project'::'CDT_System'::'Logical Architecture'::'Interfaces'::'Alert'; 
                     
                    ref :>> ownedExchangeItemAllocations =  ('CDT_System Project'::'CDT_System'::'Logical Architecture'::'Interfaces'::'Alert'.'ea25187d-22ba-4c73-bb79-7e36343a8aa1'); 
                     
                }  
                item 'SA-CDT App' : InterfaceItem  { 
                    attribute :>> isStructural = true; 
                    attribute :>> isAbstract = false; 
                    attribute :>> isFinal = false; 
                    allocation '8ceb70e3-8490-4c9f-856b-af9c506a4b22' : ExchangeItemAllocation
                        allocate allocatedItem ::> 'CDT_System Project'::'CDT_System'::'Operational Analysis'::'Data'::'Alert'
                        to allocatingInterface ::> 'CDT_System Project'::'CDT_System'::'Logical Architecture'::'Interfaces'::'SA-CDT App'; 
                    allocation '8d3c7da7-a4b1-4dbe-b483-e4f5ab268c42' : ExchangeItemAllocation
                        allocate allocatedItem ::> 'CDT_System Project'::'CDT_System'::'Operational Analysis'::'Data'::'Concussion Data'
                        to allocatingInterface ::> 'CDT_System Project'::'CDT_System'::'Logical Architecture'::'Interfaces'::'SA-CDT App'; 
                     
                    ref :>> ownedExchangeItemAllocations =  ('CDT_System Project'::'CDT_System'::'Logical Architecture'::'Interfaces'::'SA-CDT App'.'8ceb70e3-8490-4c9f-856b-af9c506a4b22',
                    'CDT_System Project'::'CDT_System'::'Logical Architecture'::'Interfaces'::'SA-CDT App'.'8d3c7da7-a4b1-4dbe-b483-e4f5ab268c42'); 
                }  
                item 'SA-CDT App' : InterfaceItem  { 
                    attribute :>> isStructural = true; 
                    attribute :>> isAbstract = false; 
                    attribute :>> isFinal = false; 
                    allocation '8380ba34-b165-4a5d-91d2-c9505842868a' : ExchangeItemAllocation
                        allocate allocatedItem ::> 'CDT_System Project'::'CDT_System'::'Operational Analysis'::'Data'::'Concussion Data'
                        to allocatingInterface ::> 'CDT_System Project'::'CDT_System'::'Logical Architecture'::'Interfaces'::'SA-CDT App'; 
                    allocation 'fdbcf818-229e-4034-bfbb-986b32cf9725' : ExchangeItemAllocation
                        allocate allocatedItem ::> 'CDT_System Project'::'CDT_System'::'Operational Analysis'::'Data'::'Report'
                        to allocatingInterface ::> 'CDT_System Project'::'CDT_System'::'Logical Architecture'::'Interfaces'::'SA-CDT App'; 
                     
                    ref :>> ownedExchangeItemAllocations =  ('CDT_System Project'::'CDT_System'::'Logical Architecture'::'Interfaces'::'SA-CDT App'.'8380ba34-b165-4a5d-91d2-c9505842868a',
                    'CDT_System Project'::'CDT_System'::'Logical Architecture'::'Interfaces'::'SA-CDT App'.'fdbcf818-229e-4034-bfbb-986b32cf9725'); 
                }  
                item 'BT - CDTApp' : InterfaceItem  { 
                    attribute :>> isStructural = true; 
                    attribute :>> isAbstract = false; 
                    attribute :>> isFinal = false; 
                    allocation '86a16862-6496-40ba-a855-6d5d5085970f' : ExchangeItemAllocation
                        allocate allocatedItem ::> 'CDT_System Project'::'CDT_System'::'Operational Analysis'::'Data'::'Concussion Data'
                        to allocatingInterface ::> 'CDT_System Project'::'CDT_System'::'Logical Architecture'::'Interfaces'::'BT - CDTApp'; 
                     
                    ref :>> ownedExchangeItemAllocations =  ('CDT_System Project'::'CDT_System'::'Logical Architecture'::'Interfaces'::'BT - CDTApp'.'86a16862-6496-40ba-a855-6d5d5085970f'); 
                }  
                item 'Lora - SA' : InterfaceItem  { 
                    attribute :>> isStructural = true; 
                    attribute :>> isAbstract = false; 
                    attribute :>> isFinal = false; 
                    allocation 'def8db49-2116-4e5e-ad54-391a7a59f78c' : ExchangeItemAllocation
                        allocate allocatedItem ::> 'CDT_System Project'::'CDT_System'::'Operational Analysis'::'Data'::'Alert'
                        to allocatingInterface ::> 'CDT_System Project'::'CDT_System'::'Logical Architecture'::'Interfaces'::'Lora - SA'; 
                     
                    ref :>> ownedExchangeItemAllocations =  ('CDT_System Project'::'CDT_System'::'Logical Architecture'::'Interfaces'::'Lora - SA'.'def8db49-2116-4e5e-ad54-391a7a59f78c'); 
                }  
                item 'SA-Inst' : InterfaceItem  { 
                    attribute :>> isStructural = true; 
                    attribute :>> isAbstract = false; 
                    attribute :>> isFinal = false; 
                    allocation '46369fae-ed7c-405a-b6ac-b2959acaf355' : ExchangeItemAllocation
                        allocate allocatedItem ::> 'CDT_System Project'::'CDT_System'::'Operational Analysis'::'Data'::'Report'
                        to allocatingInterface ::> 'CDT_System Project'::'CDT_System'::'Logical Architecture'::'Interfaces'::'SA-Inst'; 
                     
                    ref :>> ownedExchangeItemAllocations =  ('CDT_System Project'::'CDT_System'::'Logical Architecture'::'Interfaces'::'SA-Inst'.'46369fae-ed7c-405a-b6ac-b2959acaf355'); 
                }  
                item 'SA-Parent' : InterfaceItem  { 
                    attribute :>> isStructural = true; 
                    attribute :>> isAbstract = false; 
                    attribute :>> isFinal = false; 
                    allocation '5964591e-98a3-4cb1-83b2-70b983acc2a1' : ExchangeItemAllocation
                        allocate allocatedItem ::> 'CDT_System Project'::'CDT_System'::'Operational Analysis'::'Data'::'Report'
                        to allocatingInterface ::> 'CDT_System Project'::'CDT_System'::'Logical Architecture'::'Interfaces'::'SA-Parent'; 
                     
                    ref :>> ownedExchangeItemAllocations =  ('CDT_System Project'::'CDT_System'::'Logical Architecture'::'Interfaces'::'SA-Parent'.'5964591e-98a3-4cb1-83b2-70b983acc2a1'); 
                }  
                item 'SD to Lorawant' : InterfaceItem  { 
                    attribute :>> isStructural = true; 
                    attribute :>> isAbstract = false; 
                    attribute :>> isFinal = false; 
                    allocation '59623856-31fd-492e-a653-309c280cfb38' : ExchangeItemAllocation
                        allocate allocatedItem ::> 'CDT_System Project'::'CDT_System'::'Operational Analysis'::'Data'::'Alert'
                        to allocatingInterface ::> 'CDT_System Project'::'CDT_System'::'Logical Architecture'::'Interfaces'::'SD to Lorawant'; 
                     
                    ref :>> ownedExchangeItemAllocations =  ('CDT_System Project'::'CDT_System'::'Logical Architecture'::'Interfaces'::'SD to Lorawant'.'59623856-31fd-492e-a653-309c280cfb38'); 
                }  
                item 'Helmut to Sensing Device' : InterfaceItem  { 
                    attribute :>> isStructural = true; 
                    attribute :>> isAbstract = false; 
                    attribute :>> isFinal = false; 
                    allocation 'bfb93fa2-5f06-4d2e-8bab-e533a45a9adb' : ExchangeItemAllocation
                        allocate allocatedItem ::> 'CDT_System Project'::'CDT_System'::'Operational Analysis'::'Data'::'Hit'
                        to allocatingInterface ::> 'CDT_System Project'::'CDT_System'::'Logical Architecture'::'Interfaces'::'Helmut to Sensing Device'; 
                     
                    ref :>> ownedExchangeItemAllocations =  ('CDT_System Project'::'CDT_System'::'Logical Architecture'::'Interfaces'::'Helmut to Sensing Device'.'bfb93fa2-5f06-4d2e-8bab-e533a45a9adb'); 
                }  
                item 'Athlete to Helmut' : InterfaceItem  { 
                    attribute :>> isStructural = true; 
                    attribute :>> isAbstract = false; 
                    attribute :>> isFinal = false; 
                    allocation '5ba0ecf3-a8d2-4c04-bac5-b95213f62ef4' : ExchangeItemAllocation
                        allocate allocatedItem ::> 'CDT_System Project'::'CDT_System'::'Operational Analysis'::'Data'::'Hit'
                        to allocatingInterface ::> 'CDT_System Project'::'CDT_System'::'Logical Architecture'::'Interfaces'::'Athlete to Helmut'; 
                     
                    ref :>> ownedExchangeItemAllocations =  ('CDT_System Project'::'CDT_System'::'Logical Architecture'::'Interfaces'::'Athlete to Helmut'.'5ba0ecf3-a8d2-4c04-bac5-b95213f62ef4'); 
                }  
                item 'CDT App - T' : InterfaceItem  { 
                    attribute :>> isStructural = true; 
                    attribute :>> isAbstract = false; 
                    attribute :>> isFinal = false; 
                    allocation '98012b41-396e-45fb-a0e8-a4435d425274' : ExchangeItemAllocation
                        allocate allocatedItem ::> 'CDT_System Project'::'CDT_System'::'Operational Analysis'::'Data'::'Concussion Data'
                        to allocatingInterface ::> 'CDT_System Project'::'CDT_System'::'Logical Architecture'::'Interfaces'::'CDT App - T'; 
                    allocation '1bc521cd-8e1c-4ac1-b372-259face2bcc9' : ExchangeItemAllocation
                        allocate allocatedItem ::> 'CDT_System Project'::'CDT_System'::'Operational Analysis'::'Data'::'Alert'
                        to allocatingInterface ::> 'CDT_System Project'::'CDT_System'::'Logical Architecture'::'Interfaces'::'CDT App - T'; 
                     
                    ref :>> ownedExchangeItemAllocations =  ('CDT_System Project'::'CDT_System'::'Logical Architecture'::'Interfaces'::'CDT App - T'.'98012b41-396e-45fb-a0e8-a4435d425274',
                    'CDT_System Project'::'CDT_System'::'Logical Architecture'::'Interfaces'::'CDT App - T'.'1bc521cd-8e1c-4ac1-b372-259face2bcc9'); 
                }  
                item 'CDT App - T' : InterfaceItem  { 
                    attribute :>> isStructural = true; 
                    attribute :>> isAbstract = false; 
                    attribute :>> isFinal = false; 
                    allocation '947d7218-e459-4893-a0d8-ae536c1a1617' : ExchangeItemAllocation
                        allocate allocatedItem ::> 'CDT_System Project'::'CDT_System'::'Operational Analysis'::'Data'::'Policy'
                        to allocatingInterface ::> 'CDT_System Project'::'CDT_System'::'Logical Architecture'::'Interfaces'::'CDT App - T'; 
                     
                    ref :>> ownedExchangeItemAllocations =  ('CDT_System Project'::'CDT_System'::'Logical Architecture'::'Interfaces'::'CDT App - T'.'947d7218-e459-4893-a0d8-ae536c1a1617'); 
                }  
                item 'SA- Athlete' : InterfaceItem  { 
                    attribute :>> isStructural = true; 
                    attribute :>> isAbstract = false; 
                    attribute :>> isFinal = false; 
                    allocation '1c2b0790-1b2b-46b3-826a-50a13f2b6e94' : ExchangeItemAllocation
                        allocate allocatedItem ::> 'CDT_System Project'::'CDT_System'::'Operational Analysis'::'Data'::'Report'
                        to allocatingInterface ::> 'CDT_System Project'::'CDT_System'::'Logical Architecture'::'Interfaces'::'SA- Athlete'; 
                     
                    ref :>> ownedExchangeItemAllocations =  ('CDT_System Project'::'CDT_System'::'Logical Architecture'::'Interfaces'::'SA- Athlete'.'1c2b0790-1b2b-46b3-826a-50a13f2b6e94'); 
                }  
            } 
            package  'Capabilities' {
                @PackageMeta {
                    type = "CapabilityRealizationPkg";
                } 
                use case 'Maintain Device' : CapabilityRealization { 
                    ref action '9df45fbd-2917-4808-ad07-77fa5a54ff85' = 'CDT_System Project'::'CDT_System'::'Logical Architecture'::'Logical Functions'::'Root Logical Function'.'Maintain'; 
                     
                     
                }  
                use case 'Aquire Device' : CapabilityRealization { 
                    ref action 'b30366c8-66c5-46e4-81c2-87edb90ac35c' = 'CDT_System Project'::'CDT_System'::'Logical Architecture'::'Logical Functions'::'Root Logical Function'.'Acquire Device'; 
                     
                     
                }  
                use case 'Activate Detection' : CapabilityRealization { 
                    ref action 'd62c557d-2ec5-45d5-9e1b-7a4325c41ba2' = 'CDT_System Project'::'CDT_System'::'Logical Architecture'::'Logical Functions'::'Root Logical Function'.'Activate Detection Device'; 
                     
                     
                }  
                use case 'Download Data' : CapabilityRealization { 
                    ref action '69496cf1-d57e-4043-8a0d-15f2be6568f9' = 'CDT_System Project'::'CDT_System'::'Logical Architecture'::'Logical Functions'::'Root Logical Function'.'Download Data'; 
                     
                     
                }  
                use case 'Detect Concussion' : CapabilityRealization { 
                    actor 'Athlete' = 'CDT_System Project'::'CDT_System'::'Logical Architecture'::'Structure'::'Athlete'; 
                    actor 'Helmet Receives a Hit' = 'CDT_System Project'::'CDT_System'::'Logical Architecture'::'Structure'::'CDT System'.'Helmet Receives a Hit'; 
                    actor 'Sensing Device' = 'CDT_System Project'::'CDT_System'::'Logical Architecture'::'Structure'::'CDT System'.'Sensing Device'; 
                    actor 'Trainer' = 'CDT_System Project'::'CDT_System'::'Logical Architecture'::'Structure'::'Trainer'; 
                    actor 'CDT App' = 'CDT_System Project'::'CDT_System'::'Logical Architecture'::'Structure'::'CDT System'.'CDT App'; 
                    actor 'Lorawan' = 'CDT_System Project'::'CDT_System'::'Logical Architecture'::'Structure'::'CDT System'.'Lorawan'; 
                    actor 'Secure Application' = 'CDT_System Project'::'CDT_System'::'Logical Architecture'::'Structure'::'CDT System'.'Secure Application'; 
                    actor 'Instituion' = 'CDT_System Project'::'CDT_System'::'Logical Architecture'::'Structure'::'Instituion'; 
                    actor 'Parent' = 'CDT_System Project'::'CDT_System'::'Logical Architecture'::'Structure'::'Parent'; 
                    ref action 'f7cc8549-6372-4bb4-bb4d-8742284b543b' = 'CDT_System Project'::'CDT_System'::'Logical Architecture'::'Logical Functions'::'Root Logical Function'.'Detect Concussion'; 
                     
                     
                     
                }  
            } 
        } 
        package  'Physical Architecture' {
            @PackageMeta {
                type = "PhysicalArchitecture";
            } 
            package  'Data' {
                @PackageMeta {
                    type = "DataPkg";
                } 
                item 'Concussion' : Class { 
                    attribute :>> isAbstract = false; 
                    attribute :>> isFinal = false; 
                    attribute :>> isPrimitive = false; 
                }  
                item 'Activity' : Class { 
                    attribute :>> isAbstract = false; 
                    attribute :>> isFinal = false; 
                    attribute :>> isPrimitive = false; 
                }  
                item 'Activity' : ExchangeItem  { 
                    attribute :>> isAbstract = false; 
                    attribute :>> exchangeMechanism = ExchangeMechanism::EVENT; 
                    attribute :>> isFinal = false; 
                    item 'Z Accel' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                    } 
                    item 'Y Accel' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                    } 
                    item 'Z Accel' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                    } 
                    item 'X Velocity' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                    } 
                    item 'Y Velocity' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                    } 
                    item 'Z Velocity' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                    } 
                    ref :>> ownedElements =  ('CDT_System Project'::'CDT_System'::'Physical Architecture'::'Data'::'Activity'.'Z Accel',
                    'CDT_System Project'::'CDT_System'::'Physical Architecture'::'Data'::'Activity'.'Y Accel',
                    'CDT_System Project'::'CDT_System'::'Physical Architecture'::'Data'::'Activity'.'Z Accel',
                    'CDT_System Project'::'CDT_System'::'Physical Architecture'::'Data'::'Activity'.'X Velocity',
                    'CDT_System Project'::'CDT_System'::'Physical Architecture'::'Data'::'Activity'.'Y Velocity',
                    'CDT_System Project'::'CDT_System'::'Physical Architecture'::'Data'::'Activity'.'Z Velocity'); 
                }  
                item 'Concussion Data' : ExchangeItem  { 
                    attribute :>> isAbstract = false; 
                    attribute :>> exchangeMechanism = ExchangeMechanism::EVENT; 
                    attribute :>> isFinal = false; 
                    item 'Concussion' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                        ref :>> abstractType = 'CDT_System Project'::'CDT_System'::'Physical Architecture'::'Data'::'Concussion';
                    } 
                    ref :>> ownedElements =  ('CDT_System Project'::'CDT_System'::'Physical Architecture'::'Data'::'Concussion Data'.'Concussion'); 
                }  
                item 'Activity' : ExchangeItem  { 
                    attribute :>> isAbstract = false; 
                    attribute :>> exchangeMechanism = ExchangeMechanism::SHARED_DATA; 
                    attribute :>> isFinal = false; 
                    item 'Activity' : ExchangeItemElement { 
                        attribute :>> isComposite = true; 
                        attribute :>> direction = ParameterDirection::UNSET; 
                        attribute :>> isOrdered = false; 
                        attribute :>> isMaxInclusive = false; 
                        attribute :>> isMinInclusive = false; 
                        attribute :>> kind = ElementKind::TYPE; 
                        attribute :>> isUnique = false; 
                         
                         
                        ref :>> abstractType = 'CDT_System Project'::'CDT_System'::'Physical Architecture'::'Data'::'Activity';
                    } 
                    ref :>> ownedElements =  ('CDT_System Project'::'CDT_System'::'Physical Architecture'::'Data'::'Activity'.'Activity'); 
                }  
                attribute <'g'> 'g' : ARCADIAUnit; 
                attribute <'m/sec'> 'm/sec' : ARCADIAUnit; 
            } 
            package  'Physical Functions' {
                @PackageMeta {
                    type = "PhysicalFunctionPkg";
                } 
                action 'Root Physical Function' : PhysicalFunction  { 
                    attribute :>> isDerived = false; 
                    attribute :>> aggregationKind = AggregationKind::UNSET; 
                    attribute :>> isFinal = false; 
                    attribute :>> isPartOfKey = false; 
                    attribute :>> kind = FunctionKind::FUNCTION; 
                    attribute :>> isMaxInclusive = false; 
                    attribute :>> isUnique = false; 
                    attribute :>> isReadOnly = false; 
                    attribute :>> isMinInclusive = false; 
                    attribute :>> isStatic = false; 
                    attribute :>> isOrdered = false; 
                    attribute :>> isAbstract = false; 
                    action 'Acquire Device' : FunctionalChain  { 
                        attribute :>> kind = FunctionalChainKind::SIMPLE; 
                        connection 'b6e57981-4edd-4cfe-b46e-f0bb39f98fe5' : FunctionalChainInvolvementLink 
                            connect source ::> 'CDT_System Project'::'CDT_System'::'Physical Architecture'::'Physical Functions'::'Root Physical Function'.'Acquire Device'.'750a3127-d860-4819-a0a3-015e1bcf4a0e'
                            to  target ::> 'CDT_System Project'::'CDT_System'::'Physical Architecture'::'Physical Functions'::'Root Physical Function'.'Acquire Device'.'9c4af804-5507-4889-95e2-4376377b95bf' {

                                ref :>> involved = 'CDT_System Project'::'CDT_System'::'Physical Architecture'::'Physical Functions'::'Root Physical Function'.'e665875a-d1bc-4524-a7ec-836e28b52f86';

                            } 
                        ref action '9c4af804-5507-4889-95e2-4376377b95bf' = 'CDT_System Project'::'CDT_System'::'Physical Architecture'::'Physical Functions'::'Root Physical Function'.'Create profiles for Athletes'; 
                        ref action '750a3127-d860-4819-a0a3-015e1bcf4a0e' = 'CDT_System Project'::'CDT_System'::'Physical Architecture'::'Physical Functions'::'Root Physical Function'.'Provide Data for Profile'; 
                        connection '0fc82113-5b5a-4431-83e8-eb7c190d6fd1' : FunctionalChainInvolvementLink 
                            connect source ::> 'CDT_System Project'::'CDT_System'::'Physical Architecture'::'Physical Functions'::'Root Physical Function'.'Acquire Device'.'6769b719-0f2a-4e4f-a942-990c2703bcbf'
                            to  target ::> 'CDT_System Project'::'CDT_System'::'Physical Architecture'::'Physical Functions'::'Root Physical Function'.'Acquire Device'.'9c4af804-5507-4889-95e2-4376377b95bf' {

                                ref :>> involved = 'CDT_System Project'::'CDT_System'::'Physical Architecture'::'Physical Functions'::'Root Physical Function'.'491b2553-4a8f-4b59-9814-3afb66dd3774';

                            } 
                        ref action '6769b719-0f2a-4e4f-a942-990c2703bcbf' = 'CDT_System Project'::'CDT_System'::'Physical Architecture'::'Physical Functions'::'Root Physical Function'.'Aquire System'; 
                        connection '39206816-5433-4191-bc9a-a4aa03007856' : FunctionalChainInvolvementLink 
                            connect source ::> 'CDT_System Project'::'CDT_System'::'Physical Architecture'::'Physical Functions'::'Root Physical Function'.'Acquire Device'.'9c4af804-5507-4889-95e2-4376377b95bf'
                            to  target ::> 'CDT_System Project'::'CDT_System'::'Physical Architecture'::'Physical Functions'::'Root Physical Function'.'Acquire Device'.'e8ea5c8a-65b2-499d-be47-649ad916e4cc' {

                                ref :>> involved = 'CDT_System Project'::'CDT_System'::'Physical Architecture'::'Physical Functions'::'Root Physical Function'.'ac3ab92b-994d-4d14-9677-e9de084fb231';

                            } 
                        ref action '469d91ef-2b40-49b0-a3eb-28d2a891df35' = 'CDT_System Project'::'CDT_System'::'Physical Architecture'::'Physical Functions'::'Root Physical Function'.'Create Unique IDs'; 
                        connection '6629e96c-299b-4bc0-badc-021d36ebc8ed' : FunctionalChainInvolvementLink 
                            connect source ::> 'CDT_System Project'::'CDT_System'::'Physical Architecture'::'Physical Functions'::'Root Physical Function'.'Acquire Device'.'9c4af804-5507-4889-95e2-4376377b95bf'
                            to  target ::> 'CDT_System Project'::'CDT_System'::'Physical Architecture'::'Physical Functions'::'Root Physical Function'.'Acquire Device'.'469d91ef-2b40-49b0-a3eb-28d2a891df35' {

                                ref :>> involved = 'CDT_System Project'::'CDT_System'::'Physical Architecture'::'Physical Functions'::'Root Physical Function'.'7def9910-a949-4522-850b-91b33367ae40';

                            } 
                        connection 'c4fadcb3-4a80-4541-acb5-9d7927c84e2f' : FunctionalChainInvolvementLink 
                            connect source ::> 'CDT_System Project'::'CDT_System'::'Physical Architecture'::'Physical Functions'::'Root Physical Function'.'Acquire Device'.'469d91ef-2b40-49b0-a3eb-28d2a891df35'
                            to  target ::> 'CDT_System Project'::'CDT_System'::'Physical Architecture'::'Physical Functions'::'Root Physical Function'.'Acquire Device'.'5287759e-b045-4a6c-9e78-0b60b045bb5e' {

                                ref :>> involved = 'CDT_System Project'::'CDT_System'::'Physical Architecture'::'Physical Functions'::'Root Physical Function'.'17084ce1-140b-4e28-9fdf-600155068998';

                            } 
                        ref action 'ef2a80c1-33c2-4dcd-b691-d7d63560203d' = 'CDT_System Project'::'CDT_System'::'Physical Architecture'::'Physical Functions'::'Root Physical Function'.'Provide ID to Athlete'; 
                        connection 'fb415f8b-e23e-4f63-a640-daa2af091bb3' : FunctionalChainInvolvementLink 
                            connect source ::> 'CDT_System Project'::'CDT_System'::'Physical Architecture'::'Physical Functions'::'Root Physical Function'.'Acquire Device'.'d96581c3-6cc0-4d70-94f6-03ba732b8528'
                            to  target ::> 'CDT_System Project'::'CDT_System'::'Physical Architecture'::'Physical Functions'::'Root Physical Function'.'Acquire Device'.'ef2a80c1-33c2-4dcd-b691-d7d63560203d' {

                                ref :>> involved = 'CDT_System Project'::'CDT_System'::'Physical Architecture'::'Physical Functions'::'Root Physical Function'.'ed81e988-0a73-487a-8ad8-3aecdc70dd30';

                            } 
                        ref action 'b3cf4921-615d-414c-933d-18628e5c2c37' = 'CDT_System Project'::'CDT_System'::'Physical Architecture'::'Physical Functions'::'Root Physical Function'.'Recieve ID'; 
                        connection '03777834-945a-429b-bc5d-807c8886d4da' : FunctionalChainInvolvementLink 
                            connect source ::> 'CDT_System Project'::'CDT_System'::'Physical Architecture'::'Physical Functions'::'Root Physical Function'.'Acquire Device'.'ef2a80c1-33c2-4dcd-b691-d7d63560203d'
                            to  target ::> 'CDT_System Project'::'CDT_System'::'Physical Architecture'::'Physical Functions'::'Root Physical Function'.'Acquire Device'.'b3cf4921-615d-414c-933d-18628e5c2c37' {

                                ref :>> involved = 'CDT_System Project'::'CDT_System'::'Physical Architecture'::'Physical Functions'::'Root Physical Function'.'95336049-dc3c-407c-b6a4-0c7f3880f37d';

                            } 
                        ref action 'e8ea5c8a-65b2-499d-be47-649ad916e4cc' = 'CDT_System Project'::'CDT_System'::'Physical Architecture'::'Physical Functions'::'Root Physical Function'.'Store Profile'.'Gather Profile Data'; 
                        ref action '5287759e-b045-4a6c-9e78-0b60b045bb5e' = 'CDT_System Project'::'CDT_System'::'Physical Architecture'::'Physical Functions'::'Root Physical Function'.'Create Unique IDs for Athlete'.'Initiate ID Creation'; 
                        ref action 'e0acad13-aa4c-4105-88cd-e0a67f8fcd2f' = 'CDT_System Project'::'CDT_System'::'Physical Architecture'::'Physical Functions'::'Root Physical Function'.'Create Unique IDs for Athlete'.'Create ID'; 
                        connection '37328540-8f35-412b-acc4-e9f78dd0d747' : FunctionalChainInvolvementLink 
                            connect source ::> 'CDT_System Project'::'CDT_System'::'Physical Architecture'::'Physical Functions'::'Root Physical Function'.'Acquire Device'.'5287759e-b045-4a6c-9e78-0b60b045bb5e'
                            to  target ::> 'CDT_System Project'::'CDT_System'::'Physical Architecture'::'Physical Functions'::'Root Physical Function'.'Acquire Device'.'e0acad13-aa4c-4105-88cd-e0a67f8fcd2f' {

                                ref :>> involved = 'CDT_System Project'::'CDT_System'::'Physical Architecture'::'Physical Functions'::'Root Physical Function'.'Create Unique IDs for Athlete'.'147dc2ae-62f1-446c-80ed-32ffb3ecef78';

                            } 
                        connection 'a51c5626-464d-4995-b01e-e476c0f8d530' : FunctionalChainInvolvementLink 
                            connect source ::> 'CDT_System Project'::'CDT_System'::'Physical Architecture'::'Physical Functions'::'Root Physical Function'.'Acquire Device'.'e0acad13-aa4c-4105-88cd-e0a67f8fcd2f'
                            to  target ::> 'CDT_System Project'::'CDT_System'::'Physical Architecture'::'Physical Functions'::'Root Physical Function'.'Acquire Device'.'abaf8c2a-6eef-46bf-830f-272313f9632f' {

                                ref :>> involved = 'CDT_System Project'::'CDT_System'::'Physical Architecture'::'Physical Functions'::'Root Physical Function'.'Create Unique IDs for Athlete'.'c720e95c-2fd1-461d-989f-de4a3723ad3d';

                            } 
                        ref action 'e6e0e890-b524-4640-86a2-d4ce104ff401' = 'CDT_System Project'::'CDT_System'::'Physical Architecture'::'Physical Functions'::'Root Physical Function'.'Store Profile'.'Store Profile'; 
                        connection '352eab9b-f587-4c1d-b4b7-75f99e60a734' : FunctionalChainInvolvementLink 
                            connect source ::> 'CDT_System Project'::'CDT_System'::'Physical Architecture'::'Physical Functions'::'Root Physical Function'.'Acquire Device'.'e8ea5c8a-65b2-499d-be47-649ad916e4cc'
                            to  target ::> 'CDT_System Project'::'CDT_System'::'Physical Architecture'::'Physical Functions'::'Root Physical Function'.'Acquire Device'.'e6e0e890-b524-4640-86a2-d4ce104ff401' {

                                ref :>> involved = 'CDT_System Project'::'CDT_System'::'Physical Architecture'::'Physical Functions'::'Root Physical Function'.'Store Profile'.'bbf0f4ef-a3b4-4fef-846c-4126655a355e';

                            } 
                        connection 'b57b48b1-7729-42e9-976e-2f1f0ea7168d' : FunctionalChainInvolvementLink 
                            connect source ::> 'CDT_System Project'::'CDT_System'::'Physical Architecture'::'Physical Functions'::'Root Physical Function'.'Acquire Device'.'e6e0e890-b524-4640-86a2-d4ce104ff401'
                            to  target ::> 'CDT_System Project'::'CDT_System'::'Physical Architecture'::'Physical Functions'::'Root Physical Function'.'Acquire Device'.'e0acad13-aa4c-4105-88cd-e0a67f8fcd2f' {

                                ref :>> involved = 'CDT_System Project'::'CDT_System'::'Physical Architecture'::'Physical Functions'::'Root Physical Function'.'8a61ea1c-4cc3-4fd2-b046-0ff52f5d6433';

                            } 
                        ref action 'abaf8c2a-6eef-46bf-830f-272313f9632f' = 'CDT_System Project'::'CDT_System'::'Physical Architecture'::'Physical Functions'::'Root Physical Function'.'Create Unique IDs for Athlete'.'Create and Program ID'.'Get Encrypted Profile Data'; 
                        ref action 'd96581c3-6cc0-4d70-94f6-03ba732b8528' = 'CDT_System Project'::'CDT_System'::'Physical Architecture'::'Physical Functions'::'Root Physical Function'.'Create Unique IDs for Athlete'.'Create and Program ID'.'Store Encrypted ID'; 
                        ref action '9f20f670-1974-4970-b750-b8f4148be2fb' = 'CDT_System Project'::'CDT_System'::'Physical Architecture'::'Physical Functions'::'Root Physical Function'.'Create Unique IDs for Athlete'.'Create and Program ID'.'Program in ID'; 
                        connection '29444b48-b402-4c53-81ea-10e84b9d444b' : FunctionalChainInvolvementLink 
                            connect source ::> 'CDT_System Project'::'CDT_System'::'Physical Architecture'::'Physical Functions'::'Root Physical Function'.'Acquire Device'.'abaf8c2a-6eef-46bf-830f-272313f9632f'
                            to  target ::> 'CDT_System Project'::'CDT_System'::'Physical Architecture'::'Physical Functions'::'Root Physical Function'.'Acquire Device'.'9f20f670-1974-4970-b750-b8f4148be2fb' {

                                ref :>> involved = 'CDT_System Project'::'CDT_System'::'Physical Architecture'::'Physical Functions'::'Root Physical Function'.'Create Unique IDs for Athlete'.'Create and Program ID'.'f0cd1028-8747-498a-8a72-20f4a01eefdc';

                            } 
                        connection '7e33370c-3799-42c1-bac1-1267ecd8325f' : FunctionalChainInvolvementLink 
                            connect source ::> 'CDT_System Project'::'CDT_System'::'Physical Architecture'::'Physical Functions'::'Root Physical Function'.'Acquire Device'.'9f20f670-1974-4970-b750-b8f4148be2fb'
                            to  target ::> 'CDT_System Project'::'CDT_System'::'Physical Architecture'::'Physical Functions'::'Root Physical Function'.'Acquire Device'.'d96581c3-6cc0-4d70-94f6-03ba732b8528' {

                                ref :>> involved = 'CDT_System Project'::'CDT_System'::'Physical Architecture'::'Physical Functions'::'Root Physical Function'.'Create Unique IDs for Athlete'.'Create and Program ID'.'4b9d7e5b-2d87-451c-8c78-ba39e562a889';

                            } 
                         
                    }  
                    action 'Maintain' : FunctionalChain  { 
                        attribute :>> kind = FunctionalChainKind::SIMPLE; 
                        connection '9d165a85-bc1d-4418-a62d-82535a4f97b1' : FunctionalChainInvolvementLink 
                            connect source ::> 'CDT_System Project'::'CDT_System'::'Physical Architecture'::'Physical Functions'::'Root Physical Function'.'Maintain'.'72139fb6-642e-4884-b3db-2192d8225cc3'
                            to  target ::> 'CDT_System Project'::'CDT_System'::'Physical Architecture'::'Physical Functions'::'Root Physical Function'.'Maintain'.'e8b2055a-263d-4374-a5e5-f3e53dd5b768' {

                                ref :>> involved = 'CDT_System Project'::'CDT_System'::'Physical Architecture'::'Physical Functions'::'Root Physical Function'.'33df8ee7-ec53-401b-ad2d-a4b5ed379d65';

                            } 
                        ref action 'e8b2055a-263d-4374-a5e5-f3e53dd5b768' = 'CDT_System Project'::'CDT_System'::'Physical Architecture'::'Physical Functions'::'Root Physical Function'.'Assemble System Components'; 
                        ref action '72139fb6-642e-4884-b3db-2192d8225cc3' = 'CDT_System Project'::'CDT_System'::'Physical Architecture'::'Physical Functions'::'Root Physical Function'.'Aquire System'; 
                        connection 'ddcd1b4a-cb69-439e-a6e1-149133c5d893' : FunctionalChainInvolvementLink 
                            connect source ::> 'CDT_System Project'::'CDT_System'::'Physical Architecture'::'Physical Functions'::'Root Physical Function'.'Maintain'.'aa5d58ca-eeaa-45f2-b97d-812871e66b7b'
                            to  target ::> 'CDT_System Project'::'CDT_System'::'Physical Architecture'::'Physical Functions'::'Root Physical Function'.'Maintain'.'e8b2055a-263d-4374-a5e5-f3e53dd5b768' {

                                ref :>> involved = 'CDT_System Project'::'CDT_System'::'Physical Architecture'::'Physical Functions'::'Root Physical Function'.'22090920-c6f9-46bd-98bf-3d5e170f291f';

                            } 
                        ref action 'aa5d58ca-eeaa-45f2-b97d-812871e66b7b' = 'CDT_System Project'::'CDT_System'::'Physical Architecture'::'Physical Functions'::'Root Physical Function'.'Provide access to helmut mounting'; 
                        connection 'df2e5c2a-c375-4181-bcde-ea2da95970f6' : FunctionalChainInvolvementLink 
                            connect source ::> 'CDT_System Project'::'CDT_System'::'Physical Architecture'::'Physical Functions'::'Root Physical Function'.'Maintain'.'b4819f6c-a8d4-4d3e-b5fc-b08fdb11edad'
                            to  target ::> 'CDT_System Project'::'CDT_System'::'Physical Architecture'::'Physical Functions'::'Root Physical Function'.'Maintain'.'e8b2055a-263d-4374-a5e5-f3e53dd5b768' {

                                ref :>> involved = 'CDT_System Project'::'CDT_System'::'Physical Architecture'::'Physical Functions'::'Root Physical Function'.'08b5ae87-3ed6-4398-a929-d9722caebf91';

                            } 
                        ref action 'b4819f6c-a8d4-4d3e-b5fc-b08fdb11edad' = 'CDT_System Project'::'CDT_System'::'Physical Architecture'::'Physical Functions'::'Root Physical Function'.'Provide access to sensing device mounting'; 
                        connection '84671abb-0568-4cdc-8b5a-55184ec687a3' : FunctionalChainInvolvementLink 
                            connect source ::> 'CDT_System Project'::'CDT_System'::'Physical Architecture'::'Physical Functions'::'Root Physical Function'.'Maintain'.'e8b2055a-263d-4374-a5e5-f3e53dd5b768'
                            to  target ::> 'CDT_System Project'::'CDT_System'::'Physical Architecture'::'Physical Functions'::'Root Physical Function'.'Maintain'.'9392e08e-a80a-4919-98e3-41b1e6d62268' {

                                ref :>> involved = 'CDT_System Project'::'CDT_System'::'Physical Architecture'::'Physical Functions'::'Root Physical Function'.'148b6701-406e-4365-966a-60959c61b469';

                            } 
                        ref action '9392e08e-a80a-4919-98e3-41b1e6d62268' = 'CDT_System Project'::'CDT_System'::'Physical Architecture'::'Physical Functions'::'Root Physical Function'.'Prep the device for use'; 
                         
                    }  
                    action 'Activate Detection Device' : FunctionalChain  { 
                        attribute :>> kind = FunctionalChainKind::SIMPLE; 
                        connection '38e14664-e3e2-47b6-833f-eb28a4d9fdbb' : FunctionalChainInvolvementLink 
                            connect source ::> 'CDT_System Project'::'CDT_System'::'Physical Architecture'::'Physical Functions'::'Root Physical Function'.'Activate Detection Device'.'c2025142-aae0-4c5d-920e-0012e37f6e0a'
                            to  target ::> 'CDT_System Project'::'CDT_System'::'Physical Architecture'::'Physical Functions'::'Root Physical Function'.'Activate Detection Device'.'704eb5f0-43b9-4318-89af-d5e4b62dc976' {

                                ref :>> involved = 'CDT_System Project'::'CDT_System'::'Physical Architecture'::'Physical Functions'::'Root Physical Function'.'ba2b6ed1-f6cd-4a3b-98b1-83362c975fe3';

                            } 
                        ref action '704eb5f0-43b9-4318-89af-d5e4b62dc976' = 'CDT_System Project'::'CDT_System'::'Physical Architecture'::'Physical Functions'::'Root Physical Function'.'Insert ID into Sensing Device'; 
                        ref action 'c2025142-aae0-4c5d-920e-0012e37f6e0a' = 'CDT_System Project'::'CDT_System'::'Physical Architecture'::'Physical Functions'::'Root Physical Function'.'Recieve ID'; 
                        connection '909aea29-9c9e-4568-9ba0-6766f1df28fd' : FunctionalChainInvolvementLink 
                            connect source ::> 'CDT_System Project'::'CDT_System'::'Physical Architecture'::'Physical Functions'::'Root Physical Function'.'Activate Detection Device'.'704eb5f0-43b9-4318-89af-d5e4b62dc976'
                            to  target ::> 'CDT_System Project'::'CDT_System'::'Physical Architecture'::'Physical Functions'::'Root Physical Function'.'Activate Detection Device'.'7d3eb766-434a-4b7f-b8d7-408793cb1ded' {

                                ref :>> involved = 'CDT_System Project'::'CDT_System'::'Physical Architecture'::'Physical Functions'::'Root Physical Function'.'7ce6b399-9ac1-4a1b-b0d8-408b5659bcd3';

                            } 
                        ref action '7d3eb766-434a-4b7f-b8d7-408793cb1ded' = 'CDT_System Project'::'CDT_System'::'Physical Architecture'::'Physical Functions'::'Root Physical Function'.'Recieve ID'; 
                        connection 'a79e8d08-00e9-409c-b7a4-5369327ff331' : FunctionalChainInvolvementLink 
                            connect source ::> 'CDT_System Project'::'CDT_System'::'Physical Architecture'::'Physical Functions'::'Root Physical Function'.'Activate Detection Device'.'704eb5f0-43b9-4318-89af-d5e4b62dc976'
                            to  target ::> 'CDT_System Project'::'CDT_System'::'Physical Architecture'::'Physical Functions'::'Root Physical Function'.'Activate Detection Device'.'119b3f56-c0cc-4772-ae0b-4be8eeadeb3b' {

                                ref :>> involved = 'CDT_System Project'::'CDT_System'::'Physical Architecture'::'Physical Functions'::'Root Physical Function'.'7cae195c-34e2-448e-853e-b8945137813d';

                            } 
                        ref action '119b3f56-c0cc-4772-ae0b-4be8eeadeb3b' = 'CDT_System Project'::'CDT_System'::'Physical Architecture'::'Physical Functions'::'Root Physical Function'.'Place on Helmet'; 
                        connection '5c7e2452-7a20-4497-a8a7-34f09c5f1666' : FunctionalChainInvolvementLink 
                            connect source ::> 'CDT_System Project'::'CDT_System'::'Physical Architecture'::'Physical Functions'::'Root Physical Function'.'Activate Detection Device'.'7d3eb766-434a-4b7f-b8d7-408793cb1ded'
                            to  target ::> 'CDT_System Project'::'CDT_System'::'Physical Architecture'::'Physical Functions'::'Root Physical Function'.'Activate Detection Device'.'e4266f87-4911-4d5c-af37-38e302c7c2d3' {

                                ref :>> involved = 'CDT_System Project'::'CDT_System'::'Physical Architecture'::'Physical Functions'::'Root Physical Function'.'da635154-d82f-4121-91dc-7a2c0516e106';

                            } 
                        ref action 'e4266f87-4911-4d5c-af37-38e302c7c2d3' = 'CDT_System Project'::'CDT_System'::'Physical Architecture'::'Physical Functions'::'Root Physical Function'.'Enable Secure Collection'; 
                        connection 'c544b814-9445-489f-9d4f-3021bb73455d' : FunctionalChainInvolvementLink 
                            connect source ::> 'CDT_System Project'::'CDT_System'::'Physical Architecture'::'Physical Functions'::'Root Physical Function'.'Activate Detection Device'.'e4266f87-4911-4d5c-af37-38e302c7c2d3'
                            to  target ::> 'CDT_System Project'::'CDT_System'::'Physical Architecture'::'Physical Functions'::'Root Physical Function'.'Activate Detection Device'.'59deeecd-e2be-485a-8774-ee3e205e6a73' {

                                ref :>> involved = 'CDT_System Project'::'CDT_System'::'Physical Architecture'::'Physical Functions'::'Root Physical Function'.'b88170f2-5332-4406-9d71-270e24df9b11';

                            } 
                        connection 'ff666028-cbe0-4709-a399-bf72d8e74eef' : FunctionalChainInvolvementLink 
                            connect source ::> 'CDT_System Project'::'CDT_System'::'Physical Architecture'::'Physical Functions'::'Root Physical Function'.'Activate Detection Device'.'119b3f56-c0cc-4772-ae0b-4be8eeadeb3b'
                            to  target ::> 'CDT_System Project'::'CDT_System'::'Physical Architecture'::'Physical Functions'::'Root Physical Function'.'Activate Detection Device'.'a799b812-e636-4a67-a6a0-41bf909c303b' {

                                ref :>> involved = 'CDT_System Project'::'CDT_System'::'Physical Architecture'::'Physical Functions'::'Root Physical Function'.'b4f7ef4b-c36e-4150-bd3b-d844d16b02ba';

                            } 
                        ref action 'a799b812-e636-4a67-a6a0-41bf909c303b' = 'CDT_System Project'::'CDT_System'::'Physical Architecture'::'Physical Functions'::'Root Physical Function'.'Receive Athlete '; 
                        connection '45f9c33c-3c5e-421e-9cf1-3a86249eac30' : FunctionalChainInvolvementLink 
                            connect source ::> 'CDT_System Project'::'CDT_System'::'Physical Architecture'::'Physical Functions'::'Root Physical Function'.'Activate Detection Device'.'a799b812-e636-4a67-a6a0-41bf909c303b'
                            to  target ::> 'CDT_System Project'::'CDT_System'::'Physical Architecture'::'Physical Functions'::'Root Physical Function'.'Activate Detection Device'.'59deeecd-e2be-485a-8774-ee3e205e6a73' {

                                ref :>> involved = 'CDT_System Project'::'CDT_System'::'Physical Architecture'::'Physical Functions'::'Root Physical Function'.'7b17df23-af62-44ed-acba-7747c33550e5';

                            } 
                        ref action 'c665b27d-b773-4ab5-812b-dd6e7e59f510' = 'CDT_System Project'::'CDT_System'::'Physical Architecture'::'Physical Functions'::'Root Physical Function'.'Provide ID Information'; 
                        connection '7bb0cd95-7c37-49e9-b613-d82cc1633867' : FunctionalChainInvolvementLink 
                            connect source ::> 'CDT_System Project'::'CDT_System'::'Physical Architecture'::'Physical Functions'::'Root Physical Function'.'Activate Detection Device'.'c665b27d-b773-4ab5-812b-dd6e7e59f510'
                            to  target ::> 'CDT_System Project'::'CDT_System'::'Physical Architecture'::'Physical Functions'::'Root Physical Function'.'Activate Detection Device'.'e4266f87-4911-4d5c-af37-38e302c7c2d3' {

                                ref :>> involved = 'CDT_System Project'::'CDT_System'::'Physical Architecture'::'Physical Functions'::'Root Physical Function'.'7d222aa7-b806-4a69-9cab-674e9f1e0de0';

                            } 
                        ref action 'b2e81ad5-f34e-4e08-b013-ad29580d3ea9' = 'CDT_System Project'::'CDT_System'::'Physical Architecture'::'Physical Functions'::'Root Physical Function'.'Recieve Enabled Signal from Athelete Helmet'; 
                        connection '80ae2e63-7328-42e4-bcb9-ba06ddcdce10' : FunctionalChainInvolvementLink 
                            connect source ::> 'CDT_System Project'::'CDT_System'::'Physical Architecture'::'Physical Functions'::'Root Physical Function'.'Activate Detection Device'.'c343d770-f2e9-4657-a0aa-2d4a0da517cc'
                            to  target ::> 'CDT_System Project'::'CDT_System'::'Physical Architecture'::'Physical Functions'::'Root Physical Function'.'Activate Detection Device'.'b2e81ad5-f34e-4e08-b013-ad29580d3ea9' {

                                ref :>> involved = 'CDT_System Project'::'CDT_System'::'Physical Architecture'::'Physical Functions'::'Root Physical Function'.'06a84b77-2a20-41cc-9152-8af91456e9f7';

                            } 
                        ref action '59deeecd-e2be-485a-8774-ee3e205e6a73' = 'CDT_System Project'::'CDT_System'::'Physical Architecture'::'Physical Functions'::'Root Physical Function'.'Enable Monitoring'.'Enable Monitoring'; 
                        ref action 'c343d770-f2e9-4657-a0aa-2d4a0da517cc' = 'CDT_System Project'::'CDT_System'::'Physical Architecture'::'Physical Functions'::'Root Physical Function'.'Enable Monitoring'.'Enable Indicated'; 
                        connection '5e284974-deb1-435f-a059-2695c4c3f7aa' : FunctionalChainInvolvementLink 
                            connect source ::> 'CDT_System Project'::'CDT_System'::'Physical Architecture'::'Physical Functions'::'Root Physical Function'.'Activate Detection Device'.'59deeecd-e2be-485a-8774-ee3e205e6a73'
                            to  target ::> 'CDT_System Project'::'CDT_System'::'Physical Architecture'::'Physical Functions'::'Root Physical Function'.'Activate Detection Device'.'5357adcd-878f-4de7-9423-09084f706ec6' {

                                ref :>> involved = 'CDT_System Project'::'CDT_System'::'Physical Architecture'::'Physical Functions'::'Root Physical Function'.'512d646a-097e-4801-9a13-cd5ecc3487dc';

                            } 
                        ref action '9989dbcf-6a3c-48ec-a880-b9cc4aa048ed' = 'CDT_System Project'::'CDT_System'::'Physical Architecture'::'Physical Functions'::'Root Physical Function'.'Enable Monitoring'.'Look for bluetooth connect'; 
                        connection 'beabf0b1-6514-45b0-b874-c3848bce17ab' : FunctionalChainInvolvementLink 
                            connect source ::> 'CDT_System Project'::'CDT_System'::'Physical Architecture'::'Physical Functions'::'Root Physical Function'.'Activate Detection Device'.'59deeecd-e2be-485a-8774-ee3e205e6a73'
                            to  target ::> 'CDT_System Project'::'CDT_System'::'Physical Architecture'::'Physical Functions'::'Root Physical Function'.'Activate Detection Device'.'9989dbcf-6a3c-48ec-a880-b9cc4aa048ed' {

                                ref :>> involved = 'CDT_System Project'::'CDT_System'::'Physical Architecture'::'Physical Functions'::'Root Physical Function'.'Enable Monitoring'.'13e39473-1fa3-4161-bd4a-5cd862908e87';

                            } 
                        ref action '9b7ba04f-8b89-4d68-8507-c1724b217ee5' = 'CDT_System Project'::'CDT_System'::'Physical Architecture'::'Physical Functions'::'Root Physical Function'.'Enable Monitoring'.'Enable Recored'; 
                        connection '27a97c1d-be6b-4c85-bffa-ab2c4ed268e5' : FunctionalChainInvolvementLink 
                            connect source ::> 'CDT_System Project'::'CDT_System'::'Physical Architecture'::'Physical Functions'::'Root Physical Function'.'Activate Detection Device'.'5357adcd-878f-4de7-9423-09084f706ec6'
                            to  target ::> 'CDT_System Project'::'CDT_System'::'Physical Architecture'::'Physical Functions'::'Root Physical Function'.'Activate Detection Device'.'9b7ba04f-8b89-4d68-8507-c1724b217ee5' {

                                ref :>> involved = 'CDT_System Project'::'CDT_System'::'Physical Architecture'::'Physical Functions'::'Root Physical Function'.'33c7de34-5819-4162-a02e-b2d39af813fa';

                            } 
                        connection '5c7658c2-0307-4843-ad61-6a4a0e32bd00' : FunctionalChainInvolvementLink 
                            connect source ::> 'CDT_System Project'::'CDT_System'::'Physical Architecture'::'Physical Functions'::'Root Physical Function'.'Activate Detection Device'.'9b7ba04f-8b89-4d68-8507-c1724b217ee5'
                            to  target ::> 'CDT_System Project'::'CDT_System'::'Physical Architecture'::'Physical Functions'::'Root Physical Function'.'Activate Detection Device'.'c343d770-f2e9-4657-a0aa-2d4a0da517cc' {

                                ref :>> involved = 'CDT_System Project'::'CDT_System'::'Physical Architecture'::'Physical Functions'::'Root Physical Function'.'Enable Monitoring'.'a3dffb1d-7f69-44be-bf54-3573dc31d2b1';

                            } 
                        ref action '6b04b753-3bf5-49a2-b9ad-411b4573bfea' = 'CDT_System Project'::'CDT_System'::'Physical Architecture'::'Physical Functions'::'Root Physical Function'.'Enable Monitoring'.'Enable Bluetoth Connect'; 
                        connection 'caefb46e-c0a7-4827-bd6e-795a364faf04' : FunctionalChainInvolvementLink 
                            connect source ::> 'CDT_System Project'::'CDT_System'::'Physical Architecture'::'Physical Functions'::'Root Physical Function'.'Activate Detection Device'.'c343d770-f2e9-4657-a0aa-2d4a0da517cc'
                            to  target ::> 'CDT_System Project'::'CDT_System'::'Physical Architecture'::'Physical Functions'::'Root Physical Function'.'Activate Detection Device'.'6b04b753-3bf5-49a2-b9ad-411b4573bfea' {

                                ref :>> involved = 'CDT_System Project'::'CDT_System'::'Physical Architecture'::'Physical Functions'::'Root Physical Function'.'Enable Monitoring'.'05f1f0b7-40af-4fd3-9e5b-3c8c23b4ee79';

                            } 
                        connection 'ad02118a-4bd1-4d37-b1f9-acb7fdfcc20e' : FunctionalChainInvolvementLink 
                            connect source ::> 'CDT_System Project'::'CDT_System'::'Physical Architecture'::'Physical Functions'::'Root Physical Function'.'Activate Detection Device'.'6b04b753-3bf5-49a2-b9ad-411b4573bfea'
                            to  target ::> 'CDT_System Project'::'CDT_System'::'Physical Architecture'::'Physical Functions'::'Root Physical Function'.'Activate Detection Device'.'9989dbcf-6a3c-48ec-a880-b9cc4aa048ed' {

                                ref :>> involved = 'CDT_System Project'::'CDT_System'::'Physical Architecture'::'Physical Functions'::'Root Physical Function'.'Enable Monitoring'.'2c6482ad-1fc7-43d2-850c-7e17848fe27a';

                            } 
                        ref action '5357adcd-878f-4de7-9423-09084f706ec6' = 'CDT_System Project'::'CDT_System'::'Physical Architecture'::'Physical Functions'::'Root Physical Function'.'Transfer Uplink Data'; 
                         
                    }  
                    action 'Download Data' : FunctionalChain  { 
                        attribute :>> kind = FunctionalChainKind::SIMPLE; 
                        connection 'ec065aa2-d36b-4aef-ac25-c0b9d25a1f1a' : FunctionalChainInvolvementLink 
                            connect source ::> 'CDT_System Project'::'CDT_System'::'Physical Architecture'::'Physical Functions'::'Root Physical Function'.'Download Data'.'9c235a1e-7a2d-4cfa-86be-e2c3a1abcaca'
                            to  target ::> 'CDT_System Project'::'CDT_System'::'Physical Architecture'::'Physical Functions'::'Root Physical Function'.'Download Data'.'eaefb88d-3b34-4a08-921a-6e88185c1ab7' {

                                ref :>> involved = 'CDT_System Project'::'CDT_System'::'Physical Architecture'::'Physical Functions'::'Root Physical Function'.'23e5f028-b459-46de-b970-6d260ce6ca65';

                            } 
                        connection 'd4c0984e-be3c-451c-a1c1-688dd63cf014' : FunctionalChainInvolvementLink 
                            connect source ::> 'CDT_System Project'::'CDT_System'::'Physical Architecture'::'Physical Functions'::'Root Physical Function'.'Download Data'.'a645e680-f41b-4e5c-b858-bf5bc181b8e7'
                            to  target ::> 'CDT_System Project'::'CDT_System'::'Physical Architecture'::'Physical Functions'::'Root Physical Function'.'Download Data'.'b0eb68e8-cf35-41e4-89fa-eaec2410fb24' {

                                ref :>> involved = 'CDT_System Project'::'CDT_System'::'Physical Architecture'::'Physical Functions'::'Root Physical Function'.'fb33a517-f686-437b-afcf-1bfaf8863b31';

                            } 
                        ref action 'b0eb68e8-cf35-41e4-89fa-eaec2410fb24' = 'CDT_System Project'::'CDT_System'::'Physical Architecture'::'Physical Functions'::'Root Physical Function'.'Data can be reviewed'; 
                        connection 'f8a5b069-0ca0-473c-a826-24b94f1c3c12' : FunctionalChainInvolvementLink 
                            connect source ::> 'CDT_System Project'::'CDT_System'::'Physical Architecture'::'Physical Functions'::'Root Physical Function'.'Download Data'.'b0eb68e8-cf35-41e4-89fa-eaec2410fb24'
                            to  target ::> 'CDT_System Project'::'CDT_System'::'Physical Architecture'::'Physical Functions'::'Root Physical Function'.'Download Data'.'72508b12-312f-4823-8ba8-6eb8f35bc802' {

                                ref :>> involved = 'CDT_System Project'::'CDT_System'::'Physical Architecture'::'Physical Functions'::'Root Physical Function'.'68e52c77-d9b5-4ca2-9857-40506d382b2a';

                            } 
                        ref action '72508b12-312f-4823-8ba8-6eb8f35bc802' = 'CDT_System Project'::'CDT_System'::'Physical Architecture'::'Physical Functions'::'Root Physical Function'.'Executes Policies'; 
                        connection 'eb32f2e5-3528-4e7a-83d4-0e7c5c20423e' : FunctionalChainInvolvementLink 
                            connect source ::> 'CDT_System Project'::'CDT_System'::'Physical Architecture'::'Physical Functions'::'Root Physical Function'.'Download Data'.'72508b12-312f-4823-8ba8-6eb8f35bc802'
                            to  target ::> 'CDT_System Project'::'CDT_System'::'Physical Architecture'::'Physical Functions'::'Root Physical Function'.'Download Data'.'95ef921d-e46d-44f5-89a6-a8c8dbf36eda' {

                                ref :>> involved = 'CDT_System Project'::'CDT_System'::'Physical Architecture'::'Physical Functions'::'Root Physical Function'.'a8c90ff0-2958-40d5-988c-abcdfec9eb30';

                            } 
                        connection '5436c7af-2c0e-4021-b0ce-a5141e6a9658' : FunctionalChainInvolvementLink 
                            connect source ::> 'CDT_System Project'::'CDT_System'::'Physical Architecture'::'Physical Functions'::'Root Physical Function'.'Download Data'.'85784b9c-738e-446c-912e-01a4be8c0066'
                            to  target ::> 'CDT_System Project'::'CDT_System'::'Physical Architecture'::'Physical Functions'::'Root Physical Function'.'Download Data'.'93e7ae94-a299-4098-8cf1-a741c7a6e59c' {

                                ref :>> involved = 'CDT_System Project'::'CDT_System'::'Physical Architecture'::'Physical Functions'::'Root Physical Function'.'0cb04311-e193-4748-b3dd-d9e448d795ff';

                            } 
                        ref action '93e7ae94-a299-4098-8cf1-a741c7a6e59c' = 'CDT_System Project'::'CDT_System'::'Physical Architecture'::'Physical Functions'::'Root Physical Function'.'Report Received'; 
                        connection '9c6dd72b-8fdd-45fb-9817-97c4c6955ec1' : FunctionalChainInvolvementLink 
                            connect source ::> 'CDT_System Project'::'CDT_System'::'Physical Architecture'::'Physical Functions'::'Root Physical Function'.'Download Data'.'85784b9c-738e-446c-912e-01a4be8c0066'
                            to  target ::> 'CDT_System Project'::'CDT_System'::'Physical Architecture'::'Physical Functions'::'Root Physical Function'.'Download Data'.'0f24a861-1485-4c57-b811-9e82407663b6' {

                                ref :>> involved = 'CDT_System Project'::'CDT_System'::'Physical Architecture'::'Physical Functions'::'Root Physical Function'.'12ebf309-1bfb-49d3-b323-3f518edb7c44';

                            } 
                        ref action '0f24a861-1485-4c57-b811-9e82407663b6' = 'CDT_System Project'::'CDT_System'::'Physical Architecture'::'Physical Functions'::'Root Physical Function'.'Report Received'; 
                        connection '134c711e-cbff-4fc9-80e7-2b06954c086d' : FunctionalChainInvolvementLink 
                            connect source ::> 'CDT_System Project'::'CDT_System'::'Physical Architecture'::'Physical Functions'::'Root Physical Function'.'Download Data'.'85784b9c-738e-446c-912e-01a4be8c0066'
                            to  target ::> 'CDT_System Project'::'CDT_System'::'Physical Architecture'::'Physical Functions'::'Root Physical Function'.'Download Data'.'a70f44fe-0b28-44b6-b86a-b702679dd1af' {

                                ref :>> involved = 'CDT_System Project'::'CDT_System'::'Physical Architecture'::'Physical Functions'::'Root Physical Function'.'f0af47e2-b70f-4aad-b565-346bf3cfa078';

                            } 
                        ref action 'a70f44fe-0b28-44b6-b86a-b702679dd1af' = 'CDT_System Project'::'CDT_System'::'Physical Architecture'::'Physical Functions'::'Root Physical Function'.'Report received'; 
                        ref action 'eaefb88d-3b34-4a08-921a-6e88185c1ab7' = 'CDT_System Project'::'CDT_System'::'Physical Architecture'::'Physical Functions'::'Root Physical Function'.'Data stored'.'Data Stored'; 
                        ref action 'a645e680-f41b-4e5c-b858-bf5bc181b8e7' = 'CDT_System Project'::'CDT_System'::'Physical Architecture'::'Physical Functions'::'Root Physical Function'.'Data stored'.'Data is Presented'; 
                        ref action '95ef921d-e46d-44f5-89a6-a8c8dbf36eda' = 'CDT_System Project'::'CDT_System'::'Physical Architecture'::'Physical Functions'::'Root Physical Function'.'Generates Reports'.'Request Report to be sent'; 
                        ref action '85784b9c-738e-446c-912e-01a4be8c0066' = 'CDT_System Project'::'CDT_System'::'Physical Architecture'::'Physical Functions'::'Root Physical Function'.'Generates Reports'.'Generate Reports'; 
                        ref action 'e0d28985-57ad-434f-800d-acd21fff96b5' = 'CDT_System Project'::'CDT_System'::'Physical Architecture'::'Physical Functions'::'Root Physical Function'.'Data is Retrieved'.'Request the Data '; 
                        connection '62fd367c-9b5c-485a-90ed-05c86475a2c9' : FunctionalChainInvolvementLink 
                            connect source ::> 'CDT_System Project'::'CDT_System'::'Physical Architecture'::'Physical Functions'::'Root Physical Function'.'Download Data'.'9c235a1e-7a2d-4cfa-86be-e2c3a1abcaca'
                            to  target ::> 'CDT_System Project'::'CDT_System'::'Physical Architecture'::'Physical Functions'::'Root Physical Function'.'Download Data'.'e0d28985-57ad-434f-800d-acd21fff96b5' {

                                ref :>> involved = 'CDT_System Project'::'CDT_System'::'Physical Architecture'::'Physical Functions'::'Root Physical Function'.'Data is Retrieved'.'5cd7cf11-c7d2-49d3-acbd-cf965aa9c053';

                            } 
                        ref action 'fbb76e24-5544-4dbf-a687-e8753c30a06f' = 'CDT_System Project'::'CDT_System'::'Physical Architecture'::'Physical Functions'::'Root Physical Function'.'Data is Retrieved'.'Provide Hit Data'; 
                        connection 'daf6ddd7-b018-42d6-9be9-3ee17c0c98be' : FunctionalChainInvolvementLink 
                            connect source ::> 'CDT_System Project'::'CDT_System'::'Physical Architecture'::'Physical Functions'::'Root Physical Function'.'Download Data'.'e0d28985-57ad-434f-800d-acd21fff96b5'
                            to  target ::> 'CDT_System Project'::'CDT_System'::'Physical Architecture'::'Physical Functions'::'Root Physical Function'.'Download Data'.'fbb76e24-5544-4dbf-a687-e8753c30a06f' {

                                ref :>> involved = 'CDT_System Project'::'CDT_System'::'Physical Architecture'::'Physical Functions'::'Root Physical Function'.'Data is Retrieved'.'f3b6024c-0813-4c5f-9fbc-ab871dca9975';

                            } 
                        connection '7f324162-e19d-4017-bf5f-38f8907b1720' : FunctionalChainInvolvementLink 
                            connect source ::> 'CDT_System Project'::'CDT_System'::'Physical Architecture'::'Physical Functions'::'Root Physical Function'.'Download Data'.'eaefb88d-3b34-4a08-921a-6e88185c1ab7'
                            to  target ::> 'CDT_System Project'::'CDT_System'::'Physical Architecture'::'Physical Functions'::'Root Physical Function'.'Download Data'.'a645e680-f41b-4e5c-b858-bf5bc181b8e7' {

                                ref :>> involved = 'CDT_System Project'::'CDT_System'::'Physical Architecture'::'Physical Functions'::'Root Physical Function'.'Data stored'.'c2037e08-ff2e-4992-8194-54e202827a7f';

                            } 
                        connection '61e0db5d-243e-4463-953d-b941e9a14d5b' : FunctionalChainInvolvementLink 
                            connect source ::> 'CDT_System Project'::'CDT_System'::'Physical Architecture'::'Physical Functions'::'Root Physical Function'.'Download Data'.'95ef921d-e46d-44f5-89a6-a8c8dbf36eda'
                            to  target ::> 'CDT_System Project'::'CDT_System'::'Physical Architecture'::'Physical Functions'::'Root Physical Function'.'Download Data'.'85784b9c-738e-446c-912e-01a4be8c0066' {

                                ref :>> involved = 'CDT_System Project'::'CDT_System'::'Physical Architecture'::'Physical Functions'::'Root Physical Function'.'Generates Reports'.'4f5a07ad-1c1c-43f4-8ee0-2ca39f0be65b';

                            } 
                        ref action 'efa6be1f-67b5-42fe-9bc8-5c8f7242a6be' = 'CDT_System Project'::'CDT_System'::'Physical Architecture'::'Physical Functions'::'Root Physical Function'.'Data is Retrieved'.'Intitate Data Retrieval'.'Request Data'; 
                        ref action '9c235a1e-7a2d-4cfa-86be-e2c3a1abcaca' = 'CDT_System Project'::'CDT_System'::'Physical Architecture'::'Physical Functions'::'Root Physical Function'.'Data is Retrieved'.'Intitate Data Retrieval'.'Initiate Data Retrieve'; 
                        connection '36a823c6-e369-4a84-b1c0-a83b99c7dd62' : FunctionalChainInvolvementLink 
                            connect source ::> 'CDT_System Project'::'CDT_System'::'Physical Architecture'::'Physical Functions'::'Root Physical Function'.'Download Data'.'efa6be1f-67b5-42fe-9bc8-5c8f7242a6be'
                            to  target ::> 'CDT_System Project'::'CDT_System'::'Physical Architecture'::'Physical Functions'::'Root Physical Function'.'Download Data'.'9c235a1e-7a2d-4cfa-86be-e2c3a1abcaca' {

                                ref :>> involved = 'CDT_System Project'::'CDT_System'::'Physical Architecture'::'Physical Functions'::'Root Physical Function'.'Data is Retrieved'.'Intitate Data Retrieval'.'458dfb4f-1558-4285-a4b3-0dc5012da55d';

                            } 
                         
                    }  
                    action 'Detect Concussion' : FunctionalChain  { 
                        attribute :>> kind = FunctionalChainKind::SIMPLE; 
                        connection 'ac8edf02-380d-4c3a-af23-2792105cad59' : FunctionalChainInvolvementLink 
                            connect source ::> 'CDT_System Project'::'CDT_System'::'Physical Architecture'::'Physical Functions'::'Root Physical Function'.'Detect Concussion'.'78a94b18-601b-4873-9330-b91f78bf78e2'
                            to  target ::> 'CDT_System Project'::'CDT_System'::'Physical Architecture'::'Physical Functions'::'Root Physical Function'.'Detect Concussion'.'d0d86a17-3178-41ad-9e04-e20ec2af445a' {

                                ref :>> involved = 'CDT_System Project'::'CDT_System'::'Physical Architecture'::'Physical Functions'::'Root Physical Function'.'9cf0b319-b000-4762-a282-3c1bc1f8d9f2';

                            } 
                        ref action 'd0d86a17-3178-41ad-9e04-e20ec2af445a' = 'CDT_System Project'::'CDT_System'::'Physical Architecture'::'Physical Functions'::'Root Physical Function'.'Helmet Receives a Hit'; 
                        ref action '78a94b18-601b-4873-9330-b91f78bf78e2' = 'CDT_System Project'::'CDT_System'::'Physical Architecture'::'Physical Functions'::'Root Physical Function'.'Athlete Particpates in Activity'; 
                        connection 'ce76be83-947f-4a28-8433-3cb89eebbae4' : FunctionalChainInvolvementLink 
                            connect source ::> 'CDT_System Project'::'CDT_System'::'Physical Architecture'::'Physical Functions'::'Root Physical Function'.'Detect Concussion'.'d0d86a17-3178-41ad-9e04-e20ec2af445a'
                            to  target ::> 'CDT_System Project'::'CDT_System'::'Physical Architecture'::'Physical Functions'::'Root Physical Function'.'Detect Concussion'.'fde73eea-70a8-4139-8963-c7dcac7d058d' {

                                ref :>> involved = 'CDT_System Project'::'CDT_System'::'Physical Architecture'::'Physical Functions'::'Root Physical Function'.'9d36dfac-6872-4444-b1bd-2a76b69f97ad';

                            } 
                        ref action 'fde73eea-70a8-4139-8963-c7dcac7d058d' = 'CDT_System Project'::'CDT_System'::'Physical Architecture'::'Physical Functions'::'Root Physical Function'.'Device Detects Activity'; 
                        connection 'd2c68c50-b0e5-46f6-87c6-bf6280b8f8ec' : FunctionalChainInvolvementLink 
                            connect source ::> 'CDT_System Project'::'CDT_System'::'Physical Architecture'::'Physical Functions'::'Root Physical Function'.'Detect Concussion'.'fde73eea-70a8-4139-8963-c7dcac7d058d'
                            to  target ::> 'CDT_System Project'::'CDT_System'::'Physical Architecture'::'Physical Functions'::'Root Physical Function'.'Detect Concussion'.'84f47b53-a203-41ea-9ccb-f68c99170bab' {

                                ref :>> involved = 'CDT_System Project'::'CDT_System'::'Physical Architecture'::'Physical Functions'::'Root Physical Function'.'a217c874-3cbb-450a-923b-577fed855515';

                            } 
                        connection '91da883b-4e8b-4005-ba2a-ec9bb8f37be0' : FunctionalChainInvolvementLink 
                            connect source ::> 'CDT_System Project'::'CDT_System'::'Physical Architecture'::'Physical Functions'::'Root Physical Function'.'Detect Concussion'.'fde73eea-70a8-4139-8963-c7dcac7d058d'
                            to  target ::> 'CDT_System Project'::'CDT_System'::'Physical Architecture'::'Physical Functions'::'Root Physical Function'.'Detect Concussion'.'ff4e49fb-0ed3-497e-9342-76aabd2ef5cb' {

                                ref :>> involved = 'CDT_System Project'::'CDT_System'::'Physical Architecture'::'Physical Functions'::'Root Physical Function'.'51151e46-28af-4063-ad37-f00316ee0123';

                            } 
                        connection '495fcfd9-10de-4140-b974-3bb1d6fd1bec' : FunctionalChainInvolvementLink 
                            connect source ::> 'CDT_System Project'::'CDT_System'::'Physical Architecture'::'Physical Functions'::'Root Physical Function'.'Detect Concussion'.'aaa71537-e119-4337-a265-d0f81516ce84'
                            to  target ::> 'CDT_System Project'::'CDT_System'::'Physical Architecture'::'Physical Functions'::'Root Physical Function'.'Detect Concussion'.'5169db14-5cc8-467d-a1ec-72360b551a49' {

                                ref :>> involved = 'CDT_System Project'::'CDT_System'::'Physical Architecture'::'Physical Functions'::'Root Physical Function'.'497aee27-9576-4bc0-bf81-4968901d568b';

                            } 
                        ref action '5169db14-5cc8-467d-a1ec-72360b551a49' = 'CDT_System Project'::'CDT_System'::'Physical Architecture'::'Physical Functions'::'Root Physical Function'.'Trainer Recieves Concussion Alert'; 
                        ref action '84f47b53-a203-41ea-9ccb-f68c99170bab' = 'CDT_System Project'::'CDT_System'::'Physical Architecture'::'Physical Functions'::'Root Physical Function'.'Device alerts possible Concussion'.'Send message'; 
                        ref action 'aaa71537-e119-4337-a265-d0f81516ce84' = 'CDT_System Project'::'CDT_System'::'Physical Architecture'::'Physical Functions'::'Root Physical Function'.'Device alerts possible Concussion'.'Alert the Training'; 
                        connection 'a503512e-b243-4723-ab1c-72379bc95929' : FunctionalChainInvolvementLink 
                            connect source ::> 'CDT_System Project'::'CDT_System'::'Physical Architecture'::'Physical Functions'::'Root Physical Function'.'Detect Concussion'.'84f47b53-a203-41ea-9ccb-f68c99170bab'
                            to  target ::> 'CDT_System Project'::'CDT_System'::'Physical Architecture'::'Physical Functions'::'Root Physical Function'.'Detect Concussion'.'f860a7dc-bcb7-4ec5-964e-2d0f8a180326' {

                                ref :>> involved = 'CDT_System Project'::'CDT_System'::'Physical Architecture'::'Physical Functions'::'Root Physical Function'.'69140741-68f0-453d-858b-b6395ac5cdb0';

                            } 
                        ref action '96cb79d4-2816-433a-bec2-5abd7b203c47' = 'CDT_System Project'::'CDT_System'::'Physical Architecture'::'Physical Functions'::'Root Physical Function'.'Device alerts possible Concussion'.'Record the Concussion'; 
                        connection '7f861626-70db-4b02-9053-a85988e96589' : FunctionalChainInvolvementLink 
                            connect source ::> 'CDT_System Project'::'CDT_System'::'Physical Architecture'::'Physical Functions'::'Root Physical Function'.'Detect Concussion'.'f860a7dc-bcb7-4ec5-964e-2d0f8a180326'
                            to  target ::> 'CDT_System Project'::'CDT_System'::'Physical Architecture'::'Physical Functions'::'Root Physical Function'.'Detect Concussion'.'96cb79d4-2816-433a-bec2-5abd7b203c47' {

                                ref :>> involved = 'CDT_System Project'::'CDT_System'::'Physical Architecture'::'Physical Functions'::'Root Physical Function'.'47c4e8e5-b091-4e08-a377-9a091f71beac';

                            } 
                        connection 'ca804b94-57f7-4f5a-beca-2b9da8632e3c' : FunctionalChainInvolvementLink 
                            connect source ::> 'CDT_System Project'::'CDT_System'::'Physical Architecture'::'Physical Functions'::'Root Physical Function'.'Detect Concussion'.'96cb79d4-2816-433a-bec2-5abd7b203c47'
                            to  target ::> 'CDT_System Project'::'CDT_System'::'Physical Architecture'::'Physical Functions'::'Root Physical Function'.'Detect Concussion'.'aaa71537-e119-4337-a265-d0f81516ce84' {

                                ref :>> involved = 'CDT_System Project'::'CDT_System'::'Physical Architecture'::'Physical Functions'::'Root Physical Function'.'Device alerts possible Concussion'.'45e34246-c2d7-4145-9057-e7c08a0e81f0';

                            } 
                        ref action 'ff4e49fb-0ed3-497e-9342-76aabd2ef5cb' = 'CDT_System Project'::'CDT_System'::'Physical Architecture'::'Physical Functions'::'Root Physical Function'.'Data is Retrieved'.'Provide Hit Data'; 
                        ref action 'f860a7dc-bcb7-4ec5-964e-2d0f8a180326' = 'CDT_System Project'::'CDT_System'::'Physical Architecture'::'Physical Functions'::'Root Physical Function'.'Transfer Uplink Data'; 
                        connection '89b0c409-5ee1-4bc3-a142-a36721cb75fe' : FunctionalChainInvolvementLink 
                            connect source ::> 'CDT_System Project'::'CDT_System'::'Physical Architecture'::'Physical Functions'::'Root Physical Function'.'Detect Concussion'.'f860a7dc-bcb7-4ec5-964e-2d0f8a180326'
                            to  target ::> 'CDT_System Project'::'CDT_System'::'Physical Architecture'::'Physical Functions'::'Root Physical Function'.'Detect Concussion'.'96cb79d4-2816-433a-bec2-5abd7b203c47' {

                                ref :>> involved = 'CDT_System Project'::'CDT_System'::'Physical Architecture'::'Physical Functions'::'Root Physical Function'.'47c4e8e5-b091-4e08-a377-9a091f71beac';

                            } 
                         
                    }  
                    action 'Deactivate Device' : FunctionalChain  { 
                        attribute :>> kind = FunctionalChainKind::SIMPLE; 
                        connection '29e1f537-7e41-4064-892a-2ff7b7db129e' : FunctionalChainInvolvementLink 
                            connect source ::> 'CDT_System Project'::'CDT_System'::'Physical Architecture'::'Physical Functions'::'Root Physical Function'.'Deactivate Device'.'eed879fe-4dc3-403c-8237-ccb485f1e61d'
                            to  target ::> 'CDT_System Project'::'CDT_System'::'Physical Architecture'::'Physical Functions'::'Root Physical Function'.'Deactivate Device'.'f9008deb-91c7-475f-a28f-80597e22ed1c' {

                                ref :>> involved = 'CDT_System Project'::'CDT_System'::'Physical Architecture'::'Physical Functions'::'Root Physical Function'.'7f23244f-9558-4fef-b8bf-fb3cb5e42ddc';

                            } 
                        ref action 'f9008deb-91c7-475f-a28f-80597e22ed1c' = 'CDT_System Project'::'CDT_System'::'Physical Architecture'::'Physical Functions'::'Root Physical Function'.'Exit Athlete'; 
                        ref action 'eed879fe-4dc3-403c-8237-ccb485f1e61d' = 'CDT_System Project'::'CDT_System'::'Physical Architecture'::'Physical Functions'::'Root Physical Function'.'Removes Helmut'; 
                        connection 'ca33ff04-43e5-4899-bd9b-438d390945a8' : FunctionalChainInvolvementLink 
                            connect source ::> 'CDT_System Project'::'CDT_System'::'Physical Architecture'::'Physical Functions'::'Root Physical Function'.'Deactivate Device'.'f9008deb-91c7-475f-a28f-80597e22ed1c'
                            to  target ::> 'CDT_System Project'::'CDT_System'::'Physical Architecture'::'Physical Functions'::'Root Physical Function'.'Deactivate Device'.'fa92bb27-3bac-4537-9034-1998da8f15d9' {

                                ref :>> involved = 'CDT_System Project'::'CDT_System'::'Physical Architecture'::'Physical Functions'::'Root Physical Function'.'a367259a-8c5d-4679-a322-ee0fa1ab9cb1';

                            } 
                        ref action 'fa92bb27-3bac-4537-9034-1998da8f15d9' = 'CDT_System Project'::'CDT_System'::'Physical Architecture'::'Physical Functions'::'Root Physical Function'.'Disable Monitoring'; 
                         
                    }  
                    action 'Deactivate Detection Device' : FunctionalChain  { 
                        attribute :>> kind = FunctionalChainKind::SIMPLE; 
                        connection 'bfcc8408-cbde-42d9-8e15-c247ed3c3cf6' : FunctionalChainInvolvementLink 
                            connect source ::> 'CDT_System Project'::'CDT_System'::'Physical Architecture'::'Physical Functions'::'Root Physical Function'.'Deactivate Detection Device'.'de376570-5227-4b89-8178-d3576e4c2b9c'
                            to  target ::> 'CDT_System Project'::'CDT_System'::'Physical Architecture'::'Physical Functions'::'Root Physical Function'.'Deactivate Detection Device'.'b58db8c6-57b7-4b6c-9a2e-06a80dcd6d23' {

                                ref :>> involved = 'CDT_System Project'::'CDT_System'::'Physical Architecture'::'Physical Functions'::'Root Physical Function'.'95185f6a-8c82-4db9-a48c-b51e468be017';

                            } 
                        ref action 'b58db8c6-57b7-4b6c-9a2e-06a80dcd6d23' = 'CDT_System Project'::'CDT_System'::'Physical Architecture'::'Physical Functions'::'Root Physical Function'.'Disable Secure Collection'; 
                        ref action 'de376570-5227-4b89-8178-d3576e4c2b9c' = 'CDT_System Project'::'CDT_System'::'Physical Architecture'::'Physical Functions'::'Root Physical Function'.'Remove ID'; 
                         
                    }  
                    action 'Enable Monitoring' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Enable Monitoring' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inSensor Ready' : FunctionInputPort  { 
                                attribute :>> isControlType = false; 
                                attribute :>> ordering = ObjectNodeOrderingKind::FIFO; 
                                attribute :>> isControl = false; 
                                attribute :>> kindOfNode = ObjectNodeKind::Unspecified; 
                                 
                            }  
                            in port 'inHelmut Motion' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Enable Monitoring'.'Enable Monitoring'.'inSensor Ready',
                            'CDT_System Project'::'CDT_System'::'Physical Architecture'::'Physical Functions'::'Root Physical Function'.'Enable Monitoring'.'Enable Monitoring'.'inHelmut Motion'); 
                            ref :>> outputs =  ('CDT_System Project'::'CDT_System'::'Physical Architecture'::'Physical Functions'::'Root Physical Function'.'Enable Monitoring'.'Enable Monitoring'.'FOP 1',
                            'CDT_System Project'::'CDT_System'::'Physical Architecture'::'Physical Functions'::'Root Physical Function'.'Enable Monitoring'.'Enable Monitoring'.'FOP 2'); 
                             
                        }  
                        action 'Enable Recored' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Enable Monitoring'.'Enable Recored'.'FIP 1'); 
                            ref :>> outputs =  ('CDT_System Project'::'CDT_System'::'Physical Architecture'::'Physical Functions'::'Root Physical Function'.'Enable Monitoring'.'Enable Recored'.'FOP 1'); 
                             
                        }  
                        action 'Enable Indicated' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'outEnable Signal' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Enable Monitoring'.'Enable Indicated'.'FIP 1'); 
                            ref :>> outputs =  ('CDT_System Project'::'CDT_System'::'Physical Architecture'::'Physical Functions'::'Root Physical Function'.'Enable Monitoring'.'Enable Indicated'.'outEnable Signal',
                            'CDT_System Project'::'CDT_System'::'Physical Architecture'::'Physical Functions'::'Root Physical Function'.'Enable Monitoring'.'Enable Indicated'.'FOP 2'); 
                             
                        }  
                        action 'Enable Bluetoth Connect' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Enable Monitoring'.'Enable Bluetoth Connect'.'FIP 1'); 
                            ref :>> outputs =  ('CDT_System Project'::'CDT_System'::'Physical Architecture'::'Physical Functions'::'Root Physical Function'.'Enable Monitoring'.'Enable Bluetoth Connect'.'FOP 1'); 
                             
                        }  
                        action 'Look for bluetooth connect' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            in port 'FIP 2' : FunctionInputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Enable Monitoring'.'Look for bluetooth connect'.'FIP 1',
                            'CDT_System Project'::'CDT_System'::'Physical Architecture'::'Physical Functions'::'Root Physical Function'.'Enable Monitoring'.'Look for bluetooth connect'.'FIP 2'); 
                             
                            ref :>> availableInStates =  ('CDT_System Project'::'CDT_System'::'Physical Architecture'::'Structure'::'Physical System'.'Sensing Device'.'StateMachine 1'.'On'.'Hit Received'); 
                        }  
                        interface 'a3dffb1d-7f69-44be-bf54-3573dc31d2b1' : FunctionalExchange 
                            connect source ::> 'CDT_System Project'::'CDT_System'::'Physical Architecture'::'Physical Functions'::'Root Physical Function'.'Enable Monitoring'.'Enable Recored'.'FOP 1'
                            to target ::> 'CDT_System Project'::'CDT_System'::'Physical Architecture'::'Physical Functions'::'Root Physical Function'.'Enable Monitoring'.'Enable Indicated'.'FIP 1' { 
                            attribute :>> isMulticast = false; 
                            attribute :>> kindOfRate = RateKind::Unspecified; 
                            attribute :>> isMultireceive = false; 
                            attribute :>> interfaceName = "Enable"; 
                             
                        }  
                        interface '13e39473-1fa3-4161-bd4a-5cd862908e87' : FunctionalExchange 
                            connect source ::> 'CDT_System Project'::'CDT_System'::'Physical Architecture'::'Physical Functions'::'Root Physical Function'.'Enable Monitoring'.'Enable Monitoring'.'FOP 2'
                            to target ::> 'CDT_System Project'::'CDT_System'::'Physical Architecture'::'Physical Functions'::'Root Physical Function'.'Enable Monitoring'.'Look for bluetooth connect'.'FIP 1' { 
                            attribute :>> isMulticast = false; 
                            attribute :>> kindOfRate = RateKind::Unspecified; 
                            attribute :>> isMultireceive = false; 
                            attribute :>> interfaceName = "Bluetooth ready"; 
                             
                        }  
                        interface '05f1f0b7-40af-4fd3-9e5b-3c8c23b4ee79' : FunctionalExchange 
                            connect source ::> 'CDT_System Project'::'CDT_System'::'Physical Architecture'::'Physical Functions'::'Root Physical Function'.'Enable Monitoring'.'Enable Indicated'.'FOP 2'
                            to target ::> 'CDT_System Project'::'CDT_System'::'Physical Architecture'::'Physical Functions'::'Root Physical Function'.'Enable Monitoring'.'Enable Bluetoth Connect'.'FIP 1' { 
                            attribute :>> isMulticast = false; 
                            attribute :>> kindOfRate = RateKind::Unspecified; 
                            attribute :>> isMultireceive = false; 
                            attribute :>> interfaceName = "Confirm Bluetoth"; 
                             
                        }  
                        interface '2c6482ad-1fc7-43d2-850c-7e17848fe27a' : FunctionalExchange 
                            connect source ::> 'CDT_System Project'::'CDT_System'::'Physical Architecture'::'Physical Functions'::'Root Physical Function'.'Enable Monitoring'.'Enable Bluetoth Connect'.'FOP 1'
                            to target ::> 'CDT_System Project'::'CDT_System'::'Physical Architecture'::'Physical Functions'::'Root Physical Function'.'Enable Monitoring'.'Look for bluetooth connect'.'FIP 2' { 
                            attribute :>> isMulticast = false; 
                            attribute :>> kindOfRate = RateKind::Unspecified; 
                            attribute :>> isMultireceive = false; 
                            attribute :>> interfaceName = "Connect "; 
                             
                        }  
                        ref :>> ownedFunctions =  ('CDT_System Project'::'CDT_System'::'Physical Architecture'::'Physical Functions'::'Root Physical Function'.'Enable Monitoring'.'Enable Monitoring',
                        'CDT_System Project'::'CDT_System'::'Physical Architecture'::'Physical Functions'::'Root Physical Function'.'Enable Monitoring'.'Enable Recored',
                        'CDT_System Project'::'CDT_System'::'Physical Architecture'::'Physical Functions'::'Root Physical Function'.'Enable Monitoring'.'Enable Indicated',
                        'CDT_System Project'::'CDT_System'::'Physical Architecture'::'Physical Functions'::'Root Physical Function'.'Enable Monitoring'.'Enable Bluetoth Connect',
                        'CDT_System Project'::'CDT_System'::'Physical Architecture'::'Physical Functions'::'Root Physical Function'.'Enable Monitoring'.'Look for bluetooth connect'); 
                         
                        ref :>> ownedFunctionalExchanges =  ('CDT_System Project'::'CDT_System'::'Physical Architecture'::'Physical Functions'::'Root Physical Function'.'Enable Monitoring'.'a3dffb1d-7f69-44be-bf54-3573dc31d2b1',
                        'CDT_System Project'::'CDT_System'::'Physical Architecture'::'Physical Functions'::'Root Physical Function'.'Enable Monitoring'.'13e39473-1fa3-4161-bd4a-5cd862908e87',
                        'CDT_System Project'::'CDT_System'::'Physical Architecture'::'Physical Functions'::'Root Physical Function'.'Enable Monitoring'.'05f1f0b7-40af-4fd3-9e5b-3c8c23b4ee79',
                        'CDT_System Project'::'CDT_System'::'Physical Architecture'::'Physical Functions'::'Root Physical Function'.'Enable Monitoring'.'2c6482ad-1fc7-43d2-850c-7e17848fe27a'); 
                    }  
                    action 'Recieve Enabled Signal from Athelete Helmet' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inEnable Signal' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Recieve Enabled Signal from Athelete Helmet'.'inEnable Signal'); 
                         
                    }  
                    action 'Data stored' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Data Stored' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inRecorded Data' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Data stored'.'Data Stored'.'inRecorded Data'); 
                            ref :>> outputs =  ('CDT_System Project'::'CDT_System'::'Physical Architecture'::'Physical Functions'::'Root Physical Function'.'Data stored'.'Data Stored'.'FOP 1'); 
                             
                        }  
                        action 'Data is Presented' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'outStored Data ' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Data stored'.'Data is Presented'.'FIP 1'); 
                            ref :>> outputs =  ('CDT_System Project'::'CDT_System'::'Physical Architecture'::'Physical Functions'::'Root Physical Function'.'Data stored'.'Data is Presented'.'outStored Data '); 
                             
                        }  
                        interface 'c2037e08-ff2e-4992-8194-54e202827a7f' : FunctionalExchange 
                            connect source ::> 'CDT_System Project'::'CDT_System'::'Physical Architecture'::'Physical Functions'::'Root Physical Function'.'Data stored'.'Data Stored'.'FOP 1'
                            to target ::> 'CDT_System Project'::'CDT_System'::'Physical Architecture'::'Physical Functions'::'Root Physical Function'.'Data stored'.'Data is Presented'.'FIP 1' { 
                            attribute :>> isMulticast = false; 
                            attribute :>> kindOfRate = RateKind::Unspecified; 
                            attribute :>> isMultireceive = false; 
                            attribute :>> interfaceName = "Data"; 
                             
                        }  
                        ref :>> ownedFunctions =  ('CDT_System Project'::'CDT_System'::'Physical Architecture'::'Physical Functions'::'Root Physical Function'.'Data stored'.'Data Stored',
                        'CDT_System Project'::'CDT_System'::'Physical Architecture'::'Physical Functions'::'Root Physical Function'.'Data stored'.'Data is Presented'); 
                         
                        ref :>> ownedFunctionalExchanges =  ('CDT_System Project'::'CDT_System'::'Physical Architecture'::'Physical Functions'::'Root Physical Function'.'Data stored'.'c2037e08-ff2e-4992-8194-54e202827a7f'); 
                    }  
                    action 'Data can be reviewed' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inStored Data ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outInteraction 26' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Data can be reviewed'.'inStored Data '); 
                        ref :>> outputs =  ('CDT_System Project'::'CDT_System'::'Physical Architecture'::'Physical Functions'::'Root Physical Function'.'Data can be reviewed'.'outInteraction 26'); 
                         
                    }  
                    action 'Report Received' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inInstition Report' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Report Received'.'inInstition Report'); 
                         
                    }  
                    action 'Report Received' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete Report' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Report Received'.'inAthlete Report'); 
                         
                    }  
                    action 'Report received' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inParen Report' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Report received'.'inParen Report'); 
                         
                    }  
                    action 'Executes Policies' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inInteraction 26' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outExecute Policy' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Executes Policies'.'inInteraction 26'); 
                        ref :>> outputs =  ('CDT_System Project'::'CDT_System'::'Physical Architecture'::'Physical Functions'::'Root Physical Function'.'Executes Policies'.'outExecute Policy'); 
                         
                    }  
                    action 'Established Concussion Policy' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outConcussion Policy' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Established Concussion Policy'.'inSystem '); 
                        ref :>> outputs =  ('CDT_System Project'::'CDT_System'::'Physical Architecture'::'Physical Functions'::'Root Physical Function'.'Established Concussion Policy'.'outConcussion Policy'); 
                         
                    }  
                    action 'Generates Reports' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Request Report to be sent' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inExecute Policy' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Generates Reports'.'Request Report to be sent'.'inExecute Policy'); 
                            ref :>> outputs =  ('CDT_System Project'::'CDT_System'::'Physical Architecture'::'Physical Functions'::'Root Physical Function'.'Generates Reports'.'Request Report to be sent'.'FOP 1'); 
                             
                        }  
                        action 'Generate Reports' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'outParen Report' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            out port 'outInstition Report' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            out port 'outAthlete Report' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Generates Reports'.'Generate Reports'.'FIP 1'); 
                            ref :>> outputs =  ('CDT_System Project'::'CDT_System'::'Physical Architecture'::'Physical Functions'::'Root Physical Function'.'Generates Reports'.'Generate Reports'.'outParen Report',
                            'CDT_System Project'::'CDT_System'::'Physical Architecture'::'Physical Functions'::'Root Physical Function'.'Generates Reports'.'Generate Reports'.'outInstition Report',
                            'CDT_System Project'::'CDT_System'::'Physical Architecture'::'Physical Functions'::'Root Physical Function'.'Generates Reports'.'Generate Reports'.'outAthlete Report'); 
                             
                        }  
                        interface '4f5a07ad-1c1c-43f4-8ee0-2ca39f0be65b' : FunctionalExchange 
                            connect source ::> 'CDT_System Project'::'CDT_System'::'Physical Architecture'::'Physical Functions'::'Root Physical Function'.'Generates Reports'.'Request Report to be sent'.'FOP 1'
                            to target ::> 'CDT_System Project'::'CDT_System'::'Physical Architecture'::'Physical Functions'::'Root Physical Function'.'Generates Reports'.'Generate Reports'.'FIP 1' { 
                            attribute :>> isMulticast = false; 
                            attribute :>> kindOfRate = RateKind::Unspecified; 
                            attribute :>> isMultireceive = false; 
                            attribute :>> interfaceName = "Report Request"; 
                             
                        }  
                        ref :>> ownedFunctions =  ('CDT_System Project'::'CDT_System'::'Physical Architecture'::'Physical Functions'::'Root Physical Function'.'Generates Reports'.'Request Report to be sent',
                        'CDT_System Project'::'CDT_System'::'Physical Architecture'::'Physical Functions'::'Root Physical Function'.'Generates Reports'.'Generate Reports'); 
                         
                        ref :>> ownedFunctionalExchanges =  ('CDT_System Project'::'CDT_System'::'Physical Architecture'::'Physical Functions'::'Root Physical Function'.'Generates Reports'.'4f5a07ad-1c1c-43f4-8ee0-2ca39f0be65b'); 
                    }  
                    action 'Helmet Receives a Hit' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inActivity' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outHit' : FunctionOutputPort  { 
                            attribute :>> isControlType = false; 
                            attribute :>> ordering = ObjectNodeOrderingKind::FIFO; 
                            attribute :>> isControl = false; 
                            attribute :>> kindOfNode = ObjectNodeKind::Unspecified; 
                             
                            ref :>> outgoingExchangeItems =  ('CDT_System Project'::'CDT_System'::'Physical Architecture'::'Data'::'Activity'); 
                        }  
                        ref :>> inputs =  ('CDT_System Project'::'CDT_System'::'Physical Architecture'::'Physical Functions'::'Root Physical Function'.'Helmet Receives a Hit'.'inActivity'); 
                        ref :>> outputs =  ('CDT_System Project'::'CDT_System'::'Physical Architecture'::'Physical Functions'::'Root Physical Function'.'Helmet Receives a Hit'.'outHit'); 
                         
                    }  
                    action 'Enable Secure Collection' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAthlete ID' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inDevice ID ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outSensor Ready' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Enable Secure Collection'.'inAthlete ID',
                        'CDT_System Project'::'CDT_System'::'Physical Architecture'::'Physical Functions'::'Root Physical Function'.'Enable Secure Collection'.'inDevice ID '); 
                        ref :>> outputs =  ('CDT_System Project'::'CDT_System'::'Physical Architecture'::'Physical Functions'::'Root Physical Function'.'Enable Secure Collection'.'outSensor Ready'); 
                         
                    }  
                    action 'Place on Helmet' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inReady to put on Helmut' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outHead ' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Place on Helmet'.'inReady to put on Helmut'); 
                        ref :>> outputs =  ('CDT_System Project'::'CDT_System'::'Physical Architecture'::'Physical Functions'::'Root Physical Function'.'Place on Helmet'.'outHead '); 
                         
                    }  
                    action 'Device' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                         
                    }  
                    action 'Provide ID Information' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outDevice ID ' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Physical Architecture'::'Physical Functions'::'Root Physical Function'.'Provide ID Information'.'outDevice ID '); 
                         
                    }  
                    action 'Athlete Particpates in Activity' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outActivity' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Physical Architecture'::'Physical Functions'::'Root Physical Function'.'Athlete Particpates in Activity'.'outActivity'); 
                         
                    }  
                    action 'Yield to Evaluation' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAlert' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outEvaluation' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Yield to Evaluation'.'inAlert'); 
                        ref :>> outputs =  ('CDT_System Project'::'CDT_System'::'Physical Architecture'::'Physical Functions'::'Root Physical Function'.'Yield to Evaluation'.'outEvaluation'); 
                         
                    }  
                    action 'Receive Athlete ' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inHead ' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outHelmut Motion' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Receive Athlete '.'inHead '); 
                        ref :>> outputs =  ('CDT_System Project'::'CDT_System'::'Physical Architecture'::'Physical Functions'::'Root Physical Function'.'Receive Athlete '.'outHelmut Motion'); 
                         
                    }  
                    action 'Data is Retrieved' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Intitate Data Retrieval' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            action 'Evaluate Player' : PhysicalFunction  { 
                                attribute :>> isDerived = false; 
                                attribute :>> aggregationKind = AggregationKind::UNSET; 
                                attribute :>> isFinal = false; 
                                attribute :>> isPartOfKey = false; 
                                attribute :>> kind = FunctionKind::FUNCTION; 
                                attribute :>> isMaxInclusive = false; 
                                attribute :>> isUnique = false; 
                                attribute :>> isReadOnly = false; 
                                attribute :>> isMinInclusive = false; 
                                attribute :>> isStatic = false; 
                                attribute :>> isOrdered = false; 
                                attribute :>> isAbstract = false; 
                                in port 'inEvaluation' : FunctionInputPort  { 
                                    attribute :>> isControlType = false; 
                                    attribute :>> ordering = ObjectNodeOrderingKind::FIFO; 
                                    attribute :>> isControl = false; 
                                    attribute :>> kindOfNode = ObjectNodeKind::Unspecified; 
                                     
                                }  
                                in port 'FIP 2' : FunctionInputPort  { 
                                    attribute :>> isControlType = false; 
                                    attribute :>> ordering = ObjectNodeOrderingKind::FIFO; 
                                    attribute :>> isControl = false; 
                                    attribute :>> kindOfNode = ObjectNodeKind::Unspecified; 
                                     
                                }  
                                out port 'FOP 1' : FunctionOutputPort  { 
                                    attribute :>> isControlType = false; 
                                    attribute :>> ordering = ObjectNodeOrderingKind::FIFO; 
                                    attribute :>> isControl = false; 
                                    attribute :>> kindOfNode = ObjectNodeKind::Unspecified; 
                                }  
                                ref :>> inputs =  ('CDT_System Project'::'CDT_System'::'Physical Architecture'::'Physical Functions'::'Root Physical Function'.'Data is Retrieved'.'Intitate Data Retrieval'.'Evaluate Player'.'inEvaluation',
                                'CDT_System Project'::'CDT_System'::'Physical Architecture'::'Physical Functions'::'Root Physical Function'.'Data is Retrieved'.'Intitate Data Retrieval'.'Evaluate Player'.'FIP 2'); 
                                ref :>> outputs =  ('CDT_System Project'::'CDT_System'::'Physical Architecture'::'Physical Functions'::'Root Physical Function'.'Data is Retrieved'.'Intitate Data Retrieval'.'Evaluate Player'.'FOP 1'); 
                            }  
                            action 'Request Data' : PhysicalFunction  { 
                                attribute :>> isDerived = false; 
                                attribute :>> aggregationKind = AggregationKind::UNSET; 
                                attribute :>> isFinal = false; 
                                attribute :>> isPartOfKey = false; 
                                attribute :>> kind = FunctionKind::FUNCTION; 
                                attribute :>> isMaxInclusive = false; 
                                attribute :>> isUnique = false; 
                                attribute :>> isReadOnly = false; 
                                attribute :>> isMinInclusive = false; 
                                attribute :>> isStatic = false; 
                                attribute :>> isOrdered = false; 
                                attribute :>> isAbstract = false; 
                                in port 'FIP 1' : FunctionInputPort  { 
                                    attribute :>> isControlType = false; 
                                    attribute :>> ordering = ObjectNodeOrderingKind::FIFO; 
                                    attribute :>> isControl = false; 
                                    attribute :>> kindOfNode = ObjectNodeKind::Unspecified; 
                                }  
                                out port 'FOP 2' : FunctionOutputPort  { 
                                    attribute :>> isControlType = false; 
                                    attribute :>> ordering = ObjectNodeOrderingKind::FIFO; 
                                    attribute :>> isControl = false; 
                                    attribute :>> kindOfNode = ObjectNodeKind::Unspecified; 
                                     
                                }  
                                ref :>> inputs =  ('CDT_System Project'::'CDT_System'::'Physical Architecture'::'Physical Functions'::'Root Physical Function'.'Data is Retrieved'.'Intitate Data Retrieval'.'Request Data'.'FIP 1'); 
                                ref :>> outputs =  ('CDT_System Project'::'CDT_System'::'Physical Architecture'::'Physical Functions'::'Root Physical Function'.'Data is Retrieved'.'Intitate Data Retrieval'.'Request Data'.'FOP 2'); 
                            }  
                            action 'Initiate Data Retrieve' : PhysicalFunction  { 
                                attribute :>> isDerived = false; 
                                attribute :>> aggregationKind = AggregationKind::UNSET; 
                                attribute :>> isFinal = false; 
                                attribute :>> isPartOfKey = false; 
                                attribute :>> kind = FunctionKind::FUNCTION; 
                                attribute :>> isMaxInclusive = false; 
                                attribute :>> isUnique = false; 
                                attribute :>> isReadOnly = false; 
                                attribute :>> isMinInclusive = false; 
                                attribute :>> isStatic = false; 
                                attribute :>> isOrdered = false; 
                                attribute :>> isAbstract = false; 
                                in port 'FIP 1' : FunctionInputPort  { 
                                    attribute :>> isControlType = false; 
                                    attribute :>> ordering = ObjectNodeOrderingKind::FIFO; 
                                    attribute :>> isControl = false; 
                                    attribute :>> kindOfNode = ObjectNodeKind::Unspecified; 
                                     
                                }  
                                out port 'outRecorded Data' : FunctionOutputPort  { 
                                    attribute :>> isControlType = false; 
                                    attribute :>> ordering = ObjectNodeOrderingKind::FIFO; 
                                    attribute :>> isControl = false; 
                                    attribute :>> kindOfNode = ObjectNodeKind::Unspecified; 
                                     
                                }  
                                out port 'FOP 1' : FunctionOutputPort  { 
                                    attribute :>> isControlType = false; 
                                    attribute :>> ordering = ObjectNodeOrderingKind::FIFO; 
                                    attribute :>> isControl = false; 
                                    attribute :>> kindOfNode = ObjectNodeKind::Unspecified; 
                                     
                                }  
                                ref :>> inputs =  ('CDT_System Project'::'CDT_System'::'Physical Architecture'::'Physical Functions'::'Root Physical Function'.'Data is Retrieved'.'Intitate Data Retrieval'.'Initiate Data Retrieve'.'FIP 1'); 
                                ref :>> outputs =  ('CDT_System Project'::'CDT_System'::'Physical Architecture'::'Physical Functions'::'Root Physical Function'.'Data is Retrieved'.'Intitate Data Retrieval'.'Initiate Data Retrieve'.'outRecorded Data',
                                'CDT_System Project'::'CDT_System'::'Physical Architecture'::'Physical Functions'::'Root Physical Function'.'Data is Retrieved'.'Intitate Data Retrieval'.'Initiate Data Retrieve'.'FOP 1'); 
                            }  
                            interface 'a0354eb8-49cd-42ed-8a71-722fcb2e0c64' : FunctionalExchange 
                                connect source ::> 'CDT_System Project'::'CDT_System'::'Physical Architecture'::'Physical Functions'::'Root Physical Function'.'Data is Retrieved'.'Intitate Data Retrieval'.'Evaluate Player'.'FOP 1'
                                to target ::> 'CDT_System Project'::'CDT_System'::'Physical Architecture'::'Physical Functions'::'Root Physical Function'.'Data is Retrieved'.'Intitate Data Retrieval'.'Request Data'.'FIP 1' { 
                                attribute :>> isMulticast = false; 
                                attribute :>> kindOfRate = RateKind::Unspecified; 
                                attribute :>> isMultireceive = false; 
                                attribute :>> interfaceName = "Player ID"; 
                            }  
                            interface '458dfb4f-1558-4285-a4b3-0dc5012da55d' : FunctionalExchange 
                                connect source ::> 'CDT_System Project'::'CDT_System'::'Physical Architecture'::'Physical Functions'::'Root Physical Function'.'Data is Retrieved'.'Intitate Data Retrieval'.'Request Data'.'FOP 2'
                                to target ::> 'CDT_System Project'::'CDT_System'::'Physical Architecture'::'Physical Functions'::'Root Physical Function'.'Data is Retrieved'.'Intitate Data Retrieval'.'Initiate Data Retrieve'.'FIP 1' { 
                                attribute :>> isMulticast = false; 
                                attribute :>> kindOfRate = RateKind::Unspecified; 
                                attribute :>> isMultireceive = false; 
                                attribute :>> interfaceName = "Retrieve"; 
                                 
                            }  
                            ref :>> ownedFunctions =  ('CDT_System Project'::'CDT_System'::'Physical Architecture'::'Physical Functions'::'Root Physical Function'.'Data is Retrieved'.'Intitate Data Retrieval'.'Evaluate Player',
                            'CDT_System Project'::'CDT_System'::'Physical Architecture'::'Physical Functions'::'Root Physical Function'.'Data is Retrieved'.'Intitate Data Retrieval'.'Request Data',
                            'CDT_System Project'::'CDT_System'::'Physical Architecture'::'Physical Functions'::'Root Physical Function'.'Data is Retrieved'.'Intitate Data Retrieval'.'Initiate Data Retrieve'); 
                             
                            ref :>> ownedFunctionalExchanges =  ('CDT_System Project'::'CDT_System'::'Physical Architecture'::'Physical Functions'::'Root Physical Function'.'Data is Retrieved'.'Intitate Data Retrieval'.'a0354eb8-49cd-42ed-8a71-722fcb2e0c64',
                            'CDT_System Project'::'CDT_System'::'Physical Architecture'::'Physical Functions'::'Root Physical Function'.'Data is Retrieved'.'Intitate Data Retrieval'.'458dfb4f-1558-4285-a4b3-0dc5012da55d'); 
                        }  
                        action 'Request the Data ' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Data is Retrieved'.'Request the Data '.'FIP 1'); 
                            ref :>> outputs =  ('CDT_System Project'::'CDT_System'::'Physical Architecture'::'Physical Functions'::'Root Physical Function'.'Data is Retrieved'.'Request the Data '.'FOP 1'); 
                             
                        }  
                        action 'Provide Hit Data' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            in port 'inStored Data' : FunctionInputPort  { 
                                attribute :>> isControlType = false; 
                                attribute :>> ordering = ObjectNodeOrderingKind::FIFO; 
                                attribute :>> isControl = false; 
                                attribute :>> kindOfNode = ObjectNodeKind::Unspecified; 
                                ref :>> incomingExchangeItems =  ('CDT_System Project'::'CDT_System'::'Physical Architecture'::'Data'::'Activity'); 
                                 
                            }  
                            ref :>> inputs =  ('CDT_System Project'::'CDT_System'::'Physical Architecture'::'Physical Functions'::'Root Physical Function'.'Data is Retrieved'.'Provide Hit Data'.'FIP 1',
                            'CDT_System Project'::'CDT_System'::'Physical Architecture'::'Physical Functions'::'Root Physical Function'.'Data is Retrieved'.'Provide Hit Data'.'inStored Data'); 
                             
                        }  
                        interface '5cd7cf11-c7d2-49d3-acbd-cf965aa9c053' : FunctionalExchange 
                            connect source ::> 'CDT_System Project'::'CDT_System'::'Physical Architecture'::'Physical Functions'::'Root Physical Function'.'Data is Retrieved'.'Intitate Data Retrieval'.'Initiate Data Retrieve'.'FOP 1'
                            to target ::> 'CDT_System Project'::'CDT_System'::'Physical Architecture'::'Physical Functions'::'Root Physical Function'.'Data is Retrieved'.'Request the Data '.'FIP 1' { 
                            attribute :>> isMulticast = false; 
                            attribute :>> kindOfRate = RateKind::Unspecified; 
                            attribute :>> isMultireceive = false; 
                            attribute :>> interfaceName = "Data Request"; 
                             
                        }  
                        interface 'f3b6024c-0813-4c5f-9fbc-ab871dca9975' : FunctionalExchange 
                            connect source ::> 'CDT_System Project'::'CDT_System'::'Physical Architecture'::'Physical Functions'::'Root Physical Function'.'Data is Retrieved'.'Request the Data '.'FOP 1'
                            to target ::> 'CDT_System Project'::'CDT_System'::'Physical Architecture'::'Physical Functions'::'Root Physical Function'.'Data is Retrieved'.'Provide Hit Data'.'FIP 1' { 
                            attribute :>> isMulticast = false; 
                            attribute :>> kindOfRate = RateKind::Unspecified; 
                            attribute :>> isMultireceive = false; 
                            attribute :>> interfaceName = "Request"; 
                             
                        }  
                        ref :>> ownedFunctions =  ('CDT_System Project'::'CDT_System'::'Physical Architecture'::'Physical Functions'::'Root Physical Function'.'Data is Retrieved'.'Intitate Data Retrieval',
                        'CDT_System Project'::'CDT_System'::'Physical Architecture'::'Physical Functions'::'Root Physical Function'.'Data is Retrieved'.'Request the Data ',
                        'CDT_System Project'::'CDT_System'::'Physical Architecture'::'Physical Functions'::'Root Physical Function'.'Data is Retrieved'.'Provide Hit Data'); 
                         
                        ref :>> ownedFunctionalExchanges =  ('CDT_System Project'::'CDT_System'::'Physical Architecture'::'Physical Functions'::'Root Physical Function'.'Data is Retrieved'.'5cd7cf11-c7d2-49d3-acbd-cf965aa9c053',
                        'CDT_System Project'::'CDT_System'::'Physical Architecture'::'Physical Functions'::'Root Physical Function'.'Data is Retrieved'.'f3b6024c-0813-4c5f-9fbc-ab871dca9975'); 
                    }  
                    action 'Device Detects Activity' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inHit' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Physical Architecture'::'Data'::'Activity'); 
                             
                        }  
                        out port 'outConcussion' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outStored Data' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Device Detects Activity'.'inHit'); 
                        ref :>> outputs =  ('CDT_System Project'::'CDT_System'::'Physical Architecture'::'Physical Functions'::'Root Physical Function'.'Device Detects Activity'.'outConcussion',
                        'CDT_System Project'::'CDT_System'::'Physical Architecture'::'Physical Functions'::'Root Physical Function'.'Device Detects Activity'.'outStored Data'); 
                         
                        ref :>> availableInStates =  ('CDT_System Project'::'CDT_System'::'Physical Architecture'::'Structure'::'Physical System'.'Sensing Device'.'StateMachine 1'.'On'.'Monitor Activity'); 
                    }  
                    action 'Aquire System' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outSystem' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outSystem ' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outSystem' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Physical Architecture'::'Physical Functions'::'Root Physical Function'.'Aquire System'.'outSystem',
                        'CDT_System Project'::'CDT_System'::'Physical Architecture'::'Physical Functions'::'Root Physical Function'.'Aquire System'.'outSystem ',
                        'CDT_System Project'::'CDT_System'::'Physical Architecture'::'Physical Functions'::'Root Physical Function'.'Aquire System'.'outSystem'); 
                         
                    }  
                    action 'Create profiles for Athletes' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inAthlete Data' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outProfile Data' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outAthlete Profile' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Create profiles for Athletes'.'inSystem',
                        'CDT_System Project'::'CDT_System'::'Physical Architecture'::'Physical Functions'::'Root Physical Function'.'Create profiles for Athletes'.'inAthlete Data'); 
                        ref :>> outputs =  ('CDT_System Project'::'CDT_System'::'Physical Architecture'::'Physical Functions'::'Root Physical Function'.'Create profiles for Athletes'.'outProfile Data',
                        'CDT_System Project'::'CDT_System'::'Physical Architecture'::'Physical Functions'::'Root Physical Function'.'Create profiles for Athletes'.'outAthlete Profile'); 
                         
                    }  
                    action 'Create Unique IDs for Athlete' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Initiate ID Creation' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inID' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Create Unique IDs for Athlete'.'Initiate ID Creation'.'inID'); 
                            ref :>> outputs =  ('CDT_System Project'::'CDT_System'::'Physical Architecture'::'Physical Functions'::'Root Physical Function'.'Create Unique IDs for Athlete'.'Initiate ID Creation'.'FOP 1'); 
                             
                        }  
                        action 'Create ID' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            in port 'FIP 2' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Create Unique IDs for Athlete'.'Create ID'.'FIP 1',
                            'CDT_System Project'::'CDT_System'::'Physical Architecture'::'Physical Functions'::'Root Physical Function'.'Create Unique IDs for Athlete'.'Create ID'.'FIP 2'); 
                            ref :>> outputs =  ('CDT_System Project'::'CDT_System'::'Physical Architecture'::'Physical Functions'::'Root Physical Function'.'Create Unique IDs for Athlete'.'Create ID'.'FOP 1'); 
                             
                        }  
                        action 'Create and Program ID' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            action 'Get Encrypted Profile Data' : PhysicalFunction  { 
                                attribute :>> isDerived = false; 
                                attribute :>> aggregationKind = AggregationKind::UNSET; 
                                attribute :>> isFinal = false; 
                                attribute :>> isPartOfKey = false; 
                                attribute :>> kind = FunctionKind::FUNCTION; 
                                attribute :>> isMaxInclusive = false; 
                                attribute :>> isUnique = false; 
                                attribute :>> isReadOnly = false; 
                                attribute :>> isMinInclusive = false; 
                                attribute :>> isStatic = false; 
                                attribute :>> isOrdered = false; 
                                attribute :>> isAbstract = false; 
                                in port 'FIP 1' : FunctionInputPort  { 
                                    attribute :>> isControlType = false; 
                                    attribute :>> ordering = ObjectNodeOrderingKind::FIFO; 
                                    attribute :>> isControl = false; 
                                    attribute :>> kindOfNode = ObjectNodeKind::Unspecified; 
                                     
                                }  
                                out port 'FOP 1' : FunctionOutputPort  { 
                                    attribute :>> isControlType = false; 
                                    attribute :>> ordering = ObjectNodeOrderingKind::FIFO; 
                                    attribute :>> isControl = false; 
                                    attribute :>> kindOfNode = ObjectNodeKind::Unspecified; 
                                }  
                                ref :>> inputs =  ('CDT_System Project'::'CDT_System'::'Physical Architecture'::'Physical Functions'::'Root Physical Function'.'Create Unique IDs for Athlete'.'Create and Program ID'.'Get Encrypted Profile Data'.'FIP 1'); 
                                ref :>> outputs =  ('CDT_System Project'::'CDT_System'::'Physical Architecture'::'Physical Functions'::'Root Physical Function'.'Create Unique IDs for Athlete'.'Create and Program ID'.'Get Encrypted Profile Data'.'FOP 1'); 
                            }  
                            action 'Program in ID' : PhysicalFunction  { 
                                attribute :>> isDerived = false; 
                                attribute :>> aggregationKind = AggregationKind::UNSET; 
                                attribute :>> isFinal = false; 
                                attribute :>> isPartOfKey = false; 
                                attribute :>> kind = FunctionKind::FUNCTION; 
                                attribute :>> isMaxInclusive = false; 
                                attribute :>> isUnique = false; 
                                attribute :>> isReadOnly = false; 
                                attribute :>> isMinInclusive = false; 
                                attribute :>> isStatic = false; 
                                attribute :>> isOrdered = false; 
                                attribute :>> isAbstract = false; 
                                in port 'FIP 1' : FunctionInputPort  { 
                                    attribute :>> isControlType = false; 
                                    attribute :>> ordering = ObjectNodeOrderingKind::FIFO; 
                                    attribute :>> isControl = false; 
                                    attribute :>> kindOfNode = ObjectNodeKind::Unspecified; 
                                }  
                                out port 'FOP 1' : FunctionOutputPort  { 
                                    attribute :>> isControlType = false; 
                                    attribute :>> ordering = ObjectNodeOrderingKind::FIFO; 
                                    attribute :>> isControl = false; 
                                    attribute :>> kindOfNode = ObjectNodeKind::Unspecified; 
                                }  
                                ref :>> inputs =  ('CDT_System Project'::'CDT_System'::'Physical Architecture'::'Physical Functions'::'Root Physical Function'.'Create Unique IDs for Athlete'.'Create and Program ID'.'Program in ID'.'FIP 1'); 
                                ref :>> outputs =  ('CDT_System Project'::'CDT_System'::'Physical Architecture'::'Physical Functions'::'Root Physical Function'.'Create Unique IDs for Athlete'.'Create and Program ID'.'Program in ID'.'FOP 1'); 
                            }  
                            action 'Store Encrypted ID' : PhysicalFunction  { 
                                attribute :>> isDerived = false; 
                                attribute :>> aggregationKind = AggregationKind::UNSET; 
                                attribute :>> isFinal = false; 
                                attribute :>> isPartOfKey = false; 
                                attribute :>> kind = FunctionKind::FUNCTION; 
                                attribute :>> isMaxInclusive = false; 
                                attribute :>> isUnique = false; 
                                attribute :>> isReadOnly = false; 
                                attribute :>> isMinInclusive = false; 
                                attribute :>> isStatic = false; 
                                attribute :>> isOrdered = false; 
                                attribute :>> isAbstract = false; 
                                in port 'FIP 1' : FunctionInputPort  { 
                                    attribute :>> isControlType = false; 
                                    attribute :>> ordering = ObjectNodeOrderingKind::FIFO; 
                                    attribute :>> isControl = false; 
                                    attribute :>> kindOfNode = ObjectNodeKind::Unspecified; 
                                }  
                                out port 'outID Device' : FunctionOutputPort  { 
                                    attribute :>> isControlType = false; 
                                    attribute :>> ordering = ObjectNodeOrderingKind::FIFO; 
                                    attribute :>> isControl = false; 
                                    attribute :>> kindOfNode = ObjectNodeKind::Unspecified; 
                                     
                                }  
                                ref :>> inputs =  ('CDT_System Project'::'CDT_System'::'Physical Architecture'::'Physical Functions'::'Root Physical Function'.'Create Unique IDs for Athlete'.'Create and Program ID'.'Store Encrypted ID'.'FIP 1'); 
                                ref :>> outputs =  ('CDT_System Project'::'CDT_System'::'Physical Architecture'::'Physical Functions'::'Root Physical Function'.'Create Unique IDs for Athlete'.'Create and Program ID'.'Store Encrypted ID'.'outID Device'); 
                            }  
                            interface 'f0cd1028-8747-498a-8a72-20f4a01eefdc' : FunctionalExchange 
                                connect source ::> 'CDT_System Project'::'CDT_System'::'Physical Architecture'::'Physical Functions'::'Root Physical Function'.'Create Unique IDs for Athlete'.'Create and Program ID'.'Get Encrypted Profile Data'.'FOP 1'
                                to target ::> 'CDT_System Project'::'CDT_System'::'Physical Architecture'::'Physical Functions'::'Root Physical Function'.'Create Unique IDs for Athlete'.'Create and Program ID'.'Program in ID'.'FIP 1' { 
                                attribute :>> isMulticast = false; 
                                attribute :>> kindOfRate = RateKind::Unspecified; 
                                attribute :>> isMultireceive = false; 
                                attribute :>> interfaceName = "Encrypted Data"; 
                            }  
                            interface '4b9d7e5b-2d87-451c-8c78-ba39e562a889' : FunctionalExchange 
                                connect source ::> 'CDT_System Project'::'CDT_System'::'Physical Architecture'::'Physical Functions'::'Root Physical Function'.'Create Unique IDs for Athlete'.'Create and Program ID'.'Program in ID'.'FOP 1'
                                to target ::> 'CDT_System Project'::'CDT_System'::'Physical Architecture'::'Physical Functions'::'Root Physical Function'.'Create Unique IDs for Athlete'.'Create and Program ID'.'Store Encrypted ID'.'FIP 1' { 
                                attribute :>> isMulticast = false; 
                                attribute :>> kindOfRate = RateKind::Unspecified; 
                                attribute :>> isMultireceive = false; 
                                attribute :>> interfaceName = "Encrypted Data"; 
                            }  
                            ref :>> ownedFunctions =  ('CDT_System Project'::'CDT_System'::'Physical Architecture'::'Physical Functions'::'Root Physical Function'.'Create Unique IDs for Athlete'.'Create and Program ID'.'Get Encrypted Profile Data',
                            'CDT_System Project'::'CDT_System'::'Physical Architecture'::'Physical Functions'::'Root Physical Function'.'Create Unique IDs for Athlete'.'Create and Program ID'.'Program in ID',
                            'CDT_System Project'::'CDT_System'::'Physical Architecture'::'Physical Functions'::'Root Physical Function'.'Create Unique IDs for Athlete'.'Create and Program ID'.'Store Encrypted ID'); 
                             
                            ref :>> ownedFunctionalExchanges =  ('CDT_System Project'::'CDT_System'::'Physical Architecture'::'Physical Functions'::'Root Physical Function'.'Create Unique IDs for Athlete'.'Create and Program ID'.'f0cd1028-8747-498a-8a72-20f4a01eefdc',
                            'CDT_System Project'::'CDT_System'::'Physical Architecture'::'Physical Functions'::'Root Physical Function'.'Create Unique IDs for Athlete'.'Create and Program ID'.'4b9d7e5b-2d87-451c-8c78-ba39e562a889'); 
                        }  
                        interface '147dc2ae-62f1-446c-80ed-32ffb3ecef78' : FunctionalExchange 
                            connect source ::> 'CDT_System Project'::'CDT_System'::'Physical Architecture'::'Physical Functions'::'Root Physical Function'.'Create Unique IDs for Athlete'.'Initiate ID Creation'.'FOP 1'
                            to target ::> 'CDT_System Project'::'CDT_System'::'Physical Architecture'::'Physical Functions'::'Root Physical Function'.'Create Unique IDs for Athlete'.'Create ID'.'FIP 1' { 
                            attribute :>> isMulticast = false; 
                            attribute :>> kindOfRate = RateKind::Unspecified; 
                            attribute :>> isMultireceive = false; 
                            attribute :>> interfaceName = "ID Create"; 
                             
                        }  
                        interface 'c720e95c-2fd1-461d-989f-de4a3723ad3d' : FunctionalExchange 
                            connect source ::> 'CDT_System Project'::'CDT_System'::'Physical Architecture'::'Physical Functions'::'Root Physical Function'.'Create Unique IDs for Athlete'.'Create ID'.'FOP 1'
                            to target ::> 'CDT_System Project'::'CDT_System'::'Physical Architecture'::'Physical Functions'::'Root Physical Function'.'Create Unique IDs for Athlete'.'Create and Program ID'.'Get Encrypted Profile Data'.'FIP 1' { 
                            attribute :>> isMulticast = false; 
                            attribute :>> kindOfRate = RateKind::Unspecified; 
                            attribute :>> isMultireceive = false; 
                            attribute :>> interfaceName = "Program"; 
                             
                        }  
                        ref :>> ownedFunctions =  ('CDT_System Project'::'CDT_System'::'Physical Architecture'::'Physical Functions'::'Root Physical Function'.'Create Unique IDs for Athlete'.'Initiate ID Creation',
                        'CDT_System Project'::'CDT_System'::'Physical Architecture'::'Physical Functions'::'Root Physical Function'.'Create Unique IDs for Athlete'.'Create ID',
                        'CDT_System Project'::'CDT_System'::'Physical Architecture'::'Physical Functions'::'Root Physical Function'.'Create Unique IDs for Athlete'.'Create and Program ID'); 
                         
                        ref :>> ownedFunctionalExchanges =  ('CDT_System Project'::'CDT_System'::'Physical Architecture'::'Physical Functions'::'Root Physical Function'.'Create Unique IDs for Athlete'.'147dc2ae-62f1-446c-80ed-32ffb3ecef78',
                        'CDT_System Project'::'CDT_System'::'Physical Architecture'::'Physical Functions'::'Root Physical Function'.'Create Unique IDs for Athlete'.'c720e95c-2fd1-461d-989f-de4a3723ad3d'); 
                    }  
                    action 'Provide Data for Profile' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outAthlete Data' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Physical Architecture'::'Physical Functions'::'Root Physical Function'.'Provide Data for Profile'.'outAthlete Data'); 
                         
                    }  
                    action 'Recieve ID' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID Card' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Recieve ID'.'inID Card'); 
                        ref :>> outputs =  ('CDT_System Project'::'CDT_System'::'Physical Architecture'::'Physical Functions'::'Root Physical Function'.'Recieve ID'.'outID'); 
                         
                    }  
                    action 'Store Profile' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Gather Profile Data' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inAthlete Profile' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Store Profile'.'Gather Profile Data'.'inAthlete Profile'); 
                            ref :>> outputs =  ('CDT_System Project'::'CDT_System'::'Physical Architecture'::'Physical Functions'::'Root Physical Function'.'Store Profile'.'Gather Profile Data'.'FOP 1'); 
                             
                        }  
                        action 'Store Profile' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Store Profile'.'Store Profile'.'FIP 1'); 
                            ref :>> outputs =  ('CDT_System Project'::'CDT_System'::'Physical Architecture'::'Physical Functions'::'Root Physical Function'.'Store Profile'.'Store Profile'.'FOP 1'); 
                             
                        }  
                        interface 'bbf0f4ef-a3b4-4fef-846c-4126655a355e' : FunctionalExchange 
                            connect source ::> 'CDT_System Project'::'CDT_System'::'Physical Architecture'::'Physical Functions'::'Root Physical Function'.'Store Profile'.'Gather Profile Data'.'FOP 1'
                            to target ::> 'CDT_System Project'::'CDT_System'::'Physical Architecture'::'Physical Functions'::'Root Physical Function'.'Store Profile'.'Store Profile'.'FIP 1' { 
                            attribute :>> isMulticast = false; 
                            attribute :>> kindOfRate = RateKind::Unspecified; 
                            attribute :>> isMultireceive = false; 
                            attribute :>> interfaceName = "Profile Data"; 
                             
                        }  
                        ref :>> ownedFunctions =  ('CDT_System Project'::'CDT_System'::'Physical Architecture'::'Physical Functions'::'Root Physical Function'.'Store Profile'.'Gather Profile Data',
                        'CDT_System Project'::'CDT_System'::'Physical Architecture'::'Physical Functions'::'Root Physical Function'.'Store Profile'.'Store Profile'); 
                         
                        ref :>> ownedFunctionalExchanges =  ('CDT_System Project'::'CDT_System'::'Physical Architecture'::'Physical Functions'::'Root Physical Function'.'Store Profile'.'bbf0f4ef-a3b4-4fef-846c-4126655a355e'); 
                    }  
                    action 'Create Unique IDs' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inProfile Data' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Create Unique IDs'.'inProfile Data'); 
                        ref :>> outputs =  ('CDT_System Project'::'CDT_System'::'Physical Architecture'::'Physical Functions'::'Root Physical Function'.'Create Unique IDs'.'outID'); 
                         
                    }  
                    action 'Provide ID to Athlete' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID Device' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outID Card' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Provide ID to Athlete'.'inID Device'); 
                        ref :>> outputs =  ('CDT_System Project'::'CDT_System'::'Physical Architecture'::'Physical Functions'::'Root Physical Function'.'Provide ID to Athlete'.'outID Card'); 
                         
                    }  
                    action 'Assemble System Components' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inSystem' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inhelmut mounting' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'insensor mounting' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outAssembled System' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Assemble System Components'.'inSystem',
                        'CDT_System Project'::'CDT_System'::'Physical Architecture'::'Physical Functions'::'Root Physical Function'.'Assemble System Components'.'inhelmut mounting',
                        'CDT_System Project'::'CDT_System'::'Physical Architecture'::'Physical Functions'::'Root Physical Function'.'Assemble System Components'.'insensor mounting'); 
                        ref :>> outputs =  ('CDT_System Project'::'CDT_System'::'Physical Architecture'::'Physical Functions'::'Root Physical Function'.'Assemble System Components'.'outAssembled System'); 
                         
                    }  
                    action 'Provide access to helmut mounting' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outhelmut mounting' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Physical Architecture'::'Physical Functions'::'Root Physical Function'.'Provide access to helmut mounting'.'outhelmut mounting'); 
                         
                    }  
                    action 'Provide access to sensing device mounting' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'outsensor mounting' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> outputs =  ('CDT_System Project'::'CDT_System'::'Physical Architecture'::'Physical Functions'::'Root Physical Function'.'Provide access to sensing device mounting'.'outsensor mounting'); 
                         
                    }  
                    action 'Prep the device for use' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inAssembled System' : FunctionInputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Prep the device for use'.'inAssembled System'); 
                         
                    }  
                    action 'Insert ID into Sensing Device' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outReady to put on Helmut' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'outID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Insert ID into Sensing Device'.'inID'); 
                        ref :>> outputs =  ('CDT_System Project'::'CDT_System'::'Physical Architecture'::'Physical Functions'::'Root Physical Function'.'Insert ID into Sensing Device'.'outReady to put on Helmut',
                        'CDT_System Project'::'CDT_System'::'Physical Architecture'::'Physical Functions'::'Root Physical Function'.'Insert ID into Sensing Device'.'outID'); 
                         
                    }  
                    action 'Recieve ID' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inID' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outAthlete ID' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Recieve ID'.'inID'); 
                        ref :>> outputs =  ('CDT_System Project'::'CDT_System'::'Physical Architecture'::'Physical Functions'::'Root Physical Function'.'Recieve ID'.'outAthlete ID'); 
                         
                    }  
                    action 'Device alerts possible Concussion' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        action 'Send message' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'inConcussion' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 1' : FunctionOutputPort  { 
                                attribute :>> isControlType = false; 
                                attribute :>> ordering = ObjectNodeOrderingKind::FIFO; 
                                attribute :>> isControl = false; 
                                attribute :>> kindOfNode = ObjectNodeKind::Unspecified; 
                                 
                                ref :>> outgoingExchangeItems =  ('CDT_System Project'::'CDT_System'::'Physical Architecture'::'Data'::'Concussion Data'); 
                            }  
                            ref :>> inputs =  ('CDT_System Project'::'CDT_System'::'Physical Architecture'::'Physical Functions'::'Root Physical Function'.'Device alerts possible Concussion'.'Send message'.'inConcussion'); 
                            ref :>> outputs =  ('CDT_System Project'::'CDT_System'::'Physical Architecture'::'Physical Functions'::'Root Physical Function'.'Device alerts possible Concussion'.'Send message'.'FOP 1'); 
                             
                        }  
                        action 'Record the Concussion' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'FOP 2' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Device alerts possible Concussion'.'Record the Concussion'.'FIP 1'); 
                            ref :>> outputs =  ('CDT_System Project'::'CDT_System'::'Physical Architecture'::'Physical Functions'::'Root Physical Function'.'Device alerts possible Concussion'.'Record the Concussion'.'FOP 2'); 
                             
                        }  
                        action 'Alert the Training' : PhysicalFunction  { 
                            attribute :>> isDerived = false; 
                            attribute :>> aggregationKind = AggregationKind::UNSET; 
                            attribute :>> isFinal = false; 
                            attribute :>> isPartOfKey = false; 
                            attribute :>> kind = FunctionKind::FUNCTION; 
                            attribute :>> isMaxInclusive = false; 
                            attribute :>> isUnique = false; 
                            attribute :>> isReadOnly = false; 
                            attribute :>> isMinInclusive = false; 
                            attribute :>> isStatic = false; 
                            attribute :>> isOrdered = false; 
                            attribute :>> isAbstract = false; 
                            in port 'FIP 1' : FunctionInputPort  { 
                                attribute :>> isControlType = false; 
                                attribute :>> ordering = ObjectNodeOrderingKind::FIFO; 
                                attribute :>> isControl = false; 
                                attribute :>> kindOfNode = ObjectNodeKind::Unspecified; 
                                 
                            }  
                            out port 'outConcussion Alert to Trainer' : FunctionOutputPort  { 
                                attribute :>> isControlType = false; 
                                attribute :>> ordering = ObjectNodeOrderingKind::FIFO; 
                                attribute :>> isControl = false; 
                                attribute :>> kindOfNode = ObjectNodeKind::Unspecified; 
                                 
                            }  
                            ref :>> inputs =  ('CDT_System Project'::'CDT_System'::'Physical Architecture'::'Physical Functions'::'Root Physical Function'.'Device alerts possible Concussion'.'Alert the Training'.'FIP 1'); 
                            ref :>> outputs =  ('CDT_System Project'::'CDT_System'::'Physical Architecture'::'Physical Functions'::'Root Physical Function'.'Device alerts possible Concussion'.'Alert the Training'.'outConcussion Alert to Trainer'); 
                             
                        }  
                        interface '45e34246-c2d7-4145-9057-e7c08a0e81f0' : FunctionalExchange 
                            connect source ::> 'CDT_System Project'::'CDT_System'::'Physical Architecture'::'Physical Functions'::'Root Physical Function'.'Device alerts possible Concussion'.'Record the Concussion'.'FOP 2'
                            to target ::> 'CDT_System Project'::'CDT_System'::'Physical Architecture'::'Physical Functions'::'Root Physical Function'.'Device alerts possible Concussion'.'Alert the Training'.'FIP 1' { 
                            attribute :>> isMulticast = false; 
                            attribute :>> kindOfRate = RateKind::Unspecified; 
                            attribute :>> isMultireceive = false; 
                            attribute :>> interfaceName = "Concussion Alert"; 
                             
                        }  
                        ref :>> ownedFunctions =  ('CDT_System Project'::'CDT_System'::'Physical Architecture'::'Physical Functions'::'Root Physical Function'.'Device alerts possible Concussion'.'Send message',
                        'CDT_System Project'::'CDT_System'::'Physical Architecture'::'Physical Functions'::'Root Physical Function'.'Device alerts possible Concussion'.'Record the Concussion',
                        'CDT_System Project'::'CDT_System'::'Physical Architecture'::'Physical Functions'::'Root Physical Function'.'Device alerts possible Concussion'.'Alert the Training'); 
                         
                        ref :>> ownedFunctionalExchanges =  ('CDT_System Project'::'CDT_System'::'Physical Architecture'::'Physical Functions'::'Root Physical Function'.'Device alerts possible Concussion'.'45e34246-c2d7-4145-9057-e7c08a0e81f0'); 
                    }  
                    action 'Trainer Recieves Concussion Alert' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'inConcussion Policy' : FunctionInputPort  { 
                            attribute :>> isControlType = false; 
                            attribute :>> ordering = ObjectNodeOrderingKind::FIFO; 
                            attribute :>> isControl = false; 
                            attribute :>> kindOfNode = ObjectNodeKind::Unspecified; 
                             
                        }  
                        in port 'inConcussion Alert to Trainer' : FunctionInputPort  { 
                            attribute :>> isControlType = false; 
                            attribute :>> ordering = ObjectNodeOrderingKind::FIFO; 
                            attribute :>> isControl = false; 
                            attribute :>> kindOfNode = ObjectNodeKind::Unspecified; 
                             
                        }  
                        out port 'outAlert' : FunctionOutputPort  { 
                            attribute :>> isControlType = false; 
                            attribute :>> ordering = ObjectNodeOrderingKind::FIFO; 
                            attribute :>> isControl = false; 
                            attribute :>> kindOfNode = ObjectNodeKind::Unspecified; 
                             
                        }  
                        out port 'FOP 2' : FunctionOutputPort  { 
                            attribute :>> isControlType = false; 
                            attribute :>> ordering = ObjectNodeOrderingKind::FIFO; 
                            attribute :>> isControl = false; 
                            attribute :>> kindOfNode = ObjectNodeKind::Unspecified; 
                             
                        }  
                        ref :>> inputs =  ('CDT_System Project'::'CDT_System'::'Physical Architecture'::'Physical Functions'::'Root Physical Function'.'Trainer Recieves Concussion Alert'.'inConcussion Policy',
                        'CDT_System Project'::'CDT_System'::'Physical Architecture'::'Physical Functions'::'Root Physical Function'.'Trainer Recieves Concussion Alert'.'inConcussion Alert to Trainer'); 
                        ref :>> outputs =  ('CDT_System Project'::'CDT_System'::'Physical Architecture'::'Physical Functions'::'Root Physical Function'.'Trainer Recieves Concussion Alert'.'outAlert',
                        'CDT_System Project'::'CDT_System'::'Physical Architecture'::'Physical Functions'::'Root Physical Function'.'Trainer Recieves Concussion Alert'.'FOP 2'); 
                         
                    }  
                    action 'Transfer Downlink Data' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'From Cloud Console' : FunctionInputPort  { 
                            attribute :>> isControlType = false; 
                            attribute :>> ordering = ObjectNodeOrderingKind::FIFO; 
                            attribute :>> isControl = false; 
                            attribute :>> kindOfNode = ObjectNodeKind::Unspecified; 
                        }  
                        out port 'To Sensor' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Transfer Downlink Data'.'From Cloud Console'); 
                        ref :>> outputs =  ('CDT_System Project'::'CDT_System'::'Physical Architecture'::'Physical Functions'::'Root Physical Function'.'Transfer Downlink Data'.'To Sensor'); 
                    }  
                    action 'Transfer Uplink Data' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'From sensors' : FunctionInputPort  { 
                            attribute :>> isControlType = false; 
                            attribute :>> ordering = ObjectNodeOrderingKind::FIFO; 
                            attribute :>> isControl = false; 
                            attribute :>> kindOfNode = ObjectNodeKind::Unspecified; 
                            ref :>> incomingExchangeItems =  ('CDT_System Project'::'CDT_System'::'Physical Architecture'::'Data'::'Concussion Data'); 
                        }  
                        out port 'To Cloud Console' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Transfer Uplink Data'.'From sensors'); 
                        ref :>> outputs =  ('CDT_System Project'::'CDT_System'::'Physical Architecture'::'Physical Functions'::'Root Physical Function'.'Transfer Uplink Data'.'To Cloud Console'); 
                         
                    }  
                    action 'Transfer Uplink Data' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'From sensors' : FunctionInputPort  { 
                            attribute :>> isControlType = false; 
                            attribute :>> ordering = ObjectNodeOrderingKind::FIFO; 
                            attribute :>> isControl = false; 
                            attribute :>> kindOfNode = ObjectNodeKind::Unspecified; 
                        }  
                        out port 'To Cloud Console' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Transfer Uplink Data'.'From sensors'); 
                        ref :>> outputs =  ('CDT_System Project'::'CDT_System'::'Physical Architecture'::'Physical Functions'::'Root Physical Function'.'Transfer Uplink Data'.'To Cloud Console'); 
                    }  
                    action 'Transfer Downlink Data' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'From Cloud Console' : FunctionInputPort  { 
                            attribute :>> isControlType = false; 
                            attribute :>> ordering = ObjectNodeOrderingKind::FIFO; 
                            attribute :>> isControl = false; 
                            attribute :>> kindOfNode = ObjectNodeKind::Unspecified; 
                        }  
                        out port 'To Sensor' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Transfer Downlink Data'.'From Cloud Console'); 
                        ref :>> outputs =  ('CDT_System Project'::'CDT_System'::'Physical Architecture'::'Physical Functions'::'Root Physical Function'.'Transfer Downlink Data'.'To Sensor'); 
                    }  
                    action 'Removes Helmut' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'FOP 1' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'Physical Architecture'::'Physical Functions'::'Root Physical Function'.'Removes Helmut'.'FOP 1'); 
                         
                    }  
                    action 'Exit Athlete' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'FIP 1' : FunctionInputPort  { 
                            attribute :>> isControlType = false; 
                            attribute :>> ordering = ObjectNodeOrderingKind::FIFO; 
                            attribute :>> isControl = false; 
                            attribute :>> kindOfNode = ObjectNodeKind::Unspecified; 
                        }  
                        out port 'FOP 1' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Exit Athlete'.'FIP 1'); 
                        ref :>> outputs =  ('CDT_System Project'::'CDT_System'::'Physical Architecture'::'Physical Functions'::'Root Physical Function'.'Exit Athlete'.'FOP 1'); 
                         
                    }  
                    action 'Disable Monitoring' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'FIP 1' : FunctionInputPort  { 
                            attribute :>> isControlType = false; 
                            attribute :>> ordering = ObjectNodeOrderingKind::FIFO; 
                            attribute :>> isControl = false; 
                            attribute :>> kindOfNode = ObjectNodeKind::Unspecified; 
                        }  
                        in port 'FIP 2' : FunctionInputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Disable Monitoring'.'FIP 1',
                        'CDT_System Project'::'CDT_System'::'Physical Architecture'::'Physical Functions'::'Root Physical Function'.'Disable Monitoring'.'FIP 2'); 
                         
                    }  
                    action 'Remove ID' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        out port 'FOP 1' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> outputs =  ('CDT_System Project'::'CDT_System'::'Physical Architecture'::'Physical Functions'::'Root Physical Function'.'Remove ID'.'FOP 1'); 
                         
                    }  
                    action 'Disable Secure Collection' : PhysicalFunction  { 
                        attribute :>> isDerived = false; 
                        attribute :>> aggregationKind = AggregationKind::UNSET; 
                        attribute :>> isFinal = false; 
                        attribute :>> isPartOfKey = false; 
                        attribute :>> kind = FunctionKind::FUNCTION; 
                        attribute :>> isMaxInclusive = false; 
                        attribute :>> isUnique = false; 
                        attribute :>> isReadOnly = false; 
                        attribute :>> isMinInclusive = false; 
                        attribute :>> isStatic = false; 
                        attribute :>> isOrdered = false; 
                        attribute :>> isAbstract = false; 
                        in port 'FIP 1' : FunctionInputPort  { 
                            attribute :>> isControlType = false; 
                            attribute :>> ordering = ObjectNodeOrderingKind::FIFO; 
                            attribute :>> isControl = false; 
                            attribute :>> kindOfNode = ObjectNodeKind::Unspecified; 
                        }  
                        out port 'FOP 1' : FunctionOutputPort  { 
                            attribute :>> isControlType = false; 
                            attribute :>> ordering = ObjectNodeOrderingKind::FIFO; 
                            attribute :>> isControl = false; 
                            attribute :>> kindOfNode = ObjectNodeKind::Unspecified; 
                        }  
                        ref :>> inputs =  ('CDT_System Project'::'CDT_System'::'Physical Architecture'::'Physical Functions'::'Root Physical Function'.'Disable Secure Collection'.'FIP 1'); 
                        ref :>> outputs =  ('CDT_System Project'::'CDT_System'::'Physical Architecture'::'Physical Functions'::'Root Physical Function'.'Disable Secure Collection'.'FOP 1'); 
                         
                    }  
                    interface '9cf0b319-b000-4762-a282-3c1bc1f8d9f2' : FunctionalExchange 
                        connect source ::> 'CDT_System Project'::'CDT_System'::'Physical Architecture'::'Physical Functions'::'Root Physical Function'.'Athlete Particpates in Activity'.'outActivity'
                        to target ::> 'CDT_System Project'::'CDT_System'::'Physical Architecture'::'Physical Functions'::'Root Physical Function'.'Helmet Receives a Hit'.'inActivity' { 
                        attribute :>> isMulticast = false; 
                        attribute :>> kindOfRate = RateKind::Unspecified; 
                        attribute :>> isMultireceive = false; 
                        attribute :>> interfaceName = "Activity"; 
                         
                        ref :>> exchangedItems =  ('CDT_System Project'::'CDT_System'::'Physical Architecture'::'Data'::'Activity'); 
                    }  
                    interface '9d36dfac-6872-4444-b1bd-2a76b69f97ad' : FunctionalExchange 
                        connect source ::> 'CDT_System Project'::'CDT_System'::'Physical Architecture'::'Physical Functions'::'Root Physical Function'.'Helmet Receives a Hit'.'outHit'
                        to target ::> 'CDT_System Project'::'CDT_System'::'Physical Architecture'::'Physical Functions'::'Root Physical Function'.'Device Detects Activity'.'inHit' { 
                        attribute :>> isMulticast = false; 
                        attribute :>> kindOfRate = RateKind::Unspecified; 
                        attribute :>> isMultireceive = false; 
                        attribute :>> interfaceName = "Activity"; 
                         
                        ref :>> exchangedItems =  ('CDT_System Project'::'CDT_System'::'Physical Architecture'::'Data'::'Activity'); 
                    }  
                    interface 'a217c874-3cbb-450a-923b-577fed855515' : FunctionalExchange 
                        connect source ::> 'CDT_System Project'::'CDT_System'::'Physical Architecture'::'Physical Functions'::'Root Physical Function'.'Device Detects Activity'.'outConcussion'
                        to target ::> 'CDT_System Project'::'CDT_System'::'Physical Architecture'::'Physical Functions'::'Root Physical Function'.'Device alerts possible Concussion'.'Send message'.'inConcussion' { 
                        attribute :>> isMulticast = false; 
                        attribute :>> kindOfRate = RateKind::Unspecified; 
                        attribute :>> isMultireceive = false; 
                        attribute :>> interfaceName = "Concussion"; 
                         
                        ref :>> exchangedItems =  ('CDT_System Project'::'CDT_System'::'Physical Architecture'::'Data'::'Concussion Data'); 
                    }  
                    interface '51151e46-28af-4063-ad37-f00316ee0123' : FunctionalExchange 
                        connect source ::> 'CDT_System Project'::'CDT_System'::'Physical Architecture'::'Physical Functions'::'Root Physical Function'.'Device Detects Activity'.'outStored Data'
                        to target ::> 'CDT_System Project'::'CDT_System'::'Physical Architecture'::'Physical Functions'::'Root Physical Function'.'Data is Retrieved'.'Provide Hit Data'.'inStored Data' { 
                        attribute :>> isMulticast = false; 
                        attribute :>> kindOfRate = RateKind::Unspecified; 
                        attribute :>> isMultireceive = false; 
                        attribute :>> interfaceName = "Stored Data"; 
                         
                    }  
                    interface '491b2553-4a8f-4b59-9814-3afb66dd3774' : FunctionalExchange 
                        connect source ::> 'CDT_System Project'::'CDT_System'::'Physical Architecture'::'Physical Functions'::'Root Physical Function'.'Aquire System'.'outSystem'
                        to target ::> 'CDT_System Project'::'CDT_System'::'Physical Architecture'::'Physical Functions'::'Root Physical Function'.'Create profiles for Athletes'.'inSystem' { 
                        attribute :>> isMulticast = false; 
                        attribute :>> kindOfRate = RateKind::Unspecified; 
                        attribute :>> isMultireceive = false; 
                        attribute :>> interfaceName = "System"; 
                         
                    }  
                    interface 'e665875a-d1bc-4524-a7ec-836e28b52f86' : FunctionalExchange 
                        connect source ::> 'CDT_System Project'::'CDT_System'::'Physical Architecture'::'Physical Functions'::'Root Physical Function'.'Provide Data for Profile'.'outAthlete Data'
                        to target ::> 'CDT_System Project'::'CDT_System'::'Physical Architecture'::'Physical Functions'::'Root Physical Function'.'Create profiles for Athletes'.'inAthlete Data' { 
                        attribute :>> isMulticast = false; 
                        attribute :>> kindOfRate = RateKind::Unspecified; 
                        attribute :>> isMultireceive = false; 
                        attribute :>> interfaceName = "Athlete Data"; 
                         
                    }  
                    interface '7def9910-a949-4522-850b-91b33367ae40' : FunctionalExchange 
                        connect source ::> 'CDT_System Project'::'CDT_System'::'Physical Architecture'::'Physical Functions'::'Root Physical Function'.'Create profiles for Athletes'.'outProfile Data'
                        to target ::> 'CDT_System Project'::'CDT_System'::'Physical Architecture'::'Physical Functions'::'Root Physical Function'.'Create Unique IDs'.'inProfile Data' { 
                        attribute :>> isMulticast = false; 
                        attribute :>> kindOfRate = RateKind::Unspecified; 
                        attribute :>> isMultireceive = false; 
                        attribute :>> interfaceName = "Profile Data"; 
                         
                    }  
                    interface '17084ce1-140b-4e28-9fdf-600155068998' : FunctionalExchange 
                        connect source ::> 'CDT_System Project'::'CDT_System'::'Physical Architecture'::'Physical Functions'::'Root Physical Function'.'Create Unique IDs'.'outID'
                        to target ::> 'CDT_System Project'::'CDT_System'::'Physical Architecture'::'Physical Functions'::'Root Physical Function'.'Create Unique IDs for Athlete'.'Initiate ID Creation'.'inID' { 
                        attribute :>> isMulticast = false; 
                        attribute :>> kindOfRate = RateKind::Unspecified; 
                        attribute :>> isMultireceive = false; 
                        attribute :>> interfaceName = "ID"; 
                         
                    }  
                    interface 'ac3ab92b-994d-4d14-9677-e9de084fb231' : FunctionalExchange 
                        connect source ::> 'CDT_System Project'::'CDT_System'::'Physical Architecture'::'Physical Functions'::'Root Physical Function'.'Create profiles for Athletes'.'outAthlete Profile'
                        to target ::> 'CDT_System Project'::'CDT_System'::'Physical Architecture'::'Physical Functions'::'Root Physical Function'.'Store Profile'.'Gather Profile Data'.'inAthlete Profile' { 
                        attribute :>> isMulticast = false; 
                        attribute :>> kindOfRate = RateKind::Unspecified; 
                        attribute :>> isMultireceive = false; 
                        attribute :>> interfaceName = "Athlete Profile"; 
                         
                    }  
                    interface '95336049-dc3c-407c-b6a4-0c7f3880f37d' : FunctionalExchange 
                        connect source ::> 'CDT_System Project'::'CDT_System'::'Physical Architecture'::'Physical Functions'::'Root Physical Function'.'Provide ID to Athlete'.'outID Card'
                        to target ::> 'CDT_System Project'::'CDT_System'::'Physical Architecture'::'Physical Functions'::'Root Physical Function'.'Recieve ID'.'inID Card' { 
                        attribute :>> isMulticast = false; 
                        attribute :>> kindOfRate = RateKind::Unspecified; 
                        attribute :>> isMultireceive = false; 
                        attribute :>> interfaceName = "ID Card"; 
                         
                    }  
                    interface 'ed81e988-0a73-487a-8ad8-3aecdc70dd30' : FunctionalExchange 
                        connect source ::> 'CDT_System Project'::'CDT_System'::'Physical Architecture'::'Physical Functions'::'Root Physical Function'.'Create Unique IDs for Athlete'.'Create and Program ID'.'Store Encrypted ID'.'outID Device'
                        to target ::> 'CDT_System Project'::'CDT_System'::'Physical Architecture'::'Physical Functions'::'Root Physical Function'.'Provide ID to Athlete'.'inID Device' { 
                        attribute :>> isMulticast = false; 
                        attribute :>> kindOfRate = RateKind::Unspecified; 
                        attribute :>> isMultireceive = false; 
                        attribute :>> interfaceName = "ID Device"; 
                         
                    }  
                    interface '33df8ee7-ec53-401b-ad2d-a4b5ed379d65' : FunctionalExchange 
                        connect source ::> 'CDT_System Project'::'CDT_System'::'Physical Architecture'::'Physical Functions'::'Root Physical Function'.'Aquire System'.'outSystem'
                        to target ::> 'CDT_System Project'::'CDT_System'::'Physical Architecture'::'Physical Functions'::'Root Physical Function'.'Assemble System Components'.'inSystem' { 
                        attribute :>> isMulticast = false; 
                        attribute :>> kindOfRate = RateKind::Unspecified; 
                        attribute :>> isMultireceive = false; 
                        attribute :>> interfaceName = "System"; 
                         
                    }  
                    interface '22090920-c6f9-46bd-98bf-3d5e170f291f' : FunctionalExchange 
                        connect source ::> 'CDT_System Project'::'CDT_System'::'Physical Architecture'::'Physical Functions'::'Root Physical Function'.'Provide access to helmut mounting'.'outhelmut mounting'
                        to target ::> 'CDT_System Project'::'CDT_System'::'Physical Architecture'::'Physical Functions'::'Root Physical Function'.'Assemble System Components'.'inhelmut mounting' { 
                        attribute :>> isMulticast = false; 
                        attribute :>> kindOfRate = RateKind::Unspecified; 
                        attribute :>> isMultireceive = false; 
                        attribute :>> interfaceName = "helmet mounting"; 
                         
                    }  
                    interface 'da635154-d82f-4121-91dc-7a2c0516e106' : FunctionalExchange 
                        connect source ::> 'CDT_System Project'::'CDT_System'::'Physical Architecture'::'Physical Functions'::'Root Physical Function'.'Recieve ID'.'outAthlete ID'
                        to target ::> 'CDT_System Project'::'CDT_System'::'Physical Architecture'::'Physical Functions'::'Root Physical Function'.'Enable Secure Collection'.'inAthlete ID' { 
                        attribute :>> isMulticast = false; 
                        attribute :>> kindOfRate = RateKind::Unspecified; 
                        attribute :>> isMultireceive = false; 
                        attribute :>> interfaceName = "Athlete ID"; 
                         
                    }  
                    interface '08b5ae87-3ed6-4398-a929-d9722caebf91' : FunctionalExchange 
                        connect source ::> 'CDT_System Project'::'CDT_System'::'Physical Architecture'::'Physical Functions'::'Root Physical Function'.'Provide access to sensing device mounting'.'outsensor mounting'
                        to target ::> 'CDT_System Project'::'CDT_System'::'Physical Architecture'::'Physical Functions'::'Root Physical Function'.'Assemble System Components'.'insensor mounting' { 
                        attribute :>> isMulticast = false; 
                        attribute :>> kindOfRate = RateKind::Unspecified; 
                        attribute :>> isMultireceive = false; 
                        attribute :>> interfaceName = "sensor mounting"; 
                         
                    }  
                    interface '148b6701-406e-4365-966a-60959c61b469' : FunctionalExchange 
                        connect source ::> 'CDT_System Project'::'CDT_System'::'Physical Architecture'::'Physical Functions'::'Root Physical Function'.'Assemble System Components'.'outAssembled System'
                        to target ::> 'CDT_System Project'::'CDT_System'::'Physical Architecture'::'Physical Functions'::'Root Physical Function'.'Prep the device for use'.'inAssembled System' { 
                        attribute :>> isMulticast = false; 
                        attribute :>> kindOfRate = RateKind::Unspecified; 
                        attribute :>> isMultireceive = false; 
                        attribute :>> interfaceName = "Assembled System"; 
                         
                    }  
                    interface 'ba2b6ed1-f6cd-4a3b-98b1-83362c975fe3' : FunctionalExchange 
                        connect source ::> 'CDT_System Project'::'CDT_System'::'Physical Architecture'::'Physical Functions'::'Root Physical Function'.'Recieve ID'.'outID'
                        to target ::> 'CDT_System Project'::'CDT_System'::'Physical Architecture'::'Physical Functions'::'Root Physical Function'.'Insert ID into Sensing Device'.'inID' { 
                        attribute :>> isMulticast = false; 
                        attribute :>> kindOfRate = RateKind::Unspecified; 
                        attribute :>> isMultireceive = false; 
                        attribute :>> interfaceName = "ID"; 
                         
                    }  
                    interface '7ce6b399-9ac1-4a1b-b0d8-408b5659bcd3' : FunctionalExchange 
                        connect source ::> 'CDT_System Project'::'CDT_System'::'Physical Architecture'::'Physical Functions'::'Root Physical Function'.'Insert ID into Sensing Device'.'outID'
                        to target ::> 'CDT_System Project'::'CDT_System'::'Physical Architecture'::'Physical Functions'::'Root Physical Function'.'Recieve ID'.'inID' { 
                        attribute :>> isMulticast = false; 
                        attribute :>> kindOfRate = RateKind::Unspecified; 
                        attribute :>> isMultireceive = false; 
                        attribute :>> interfaceName = "ID Inserted"; 
                         
                    }  
                    interface '7b17df23-af62-44ed-acba-7747c33550e5' : FunctionalExchange 
                        connect source ::> 'CDT_System Project'::'CDT_System'::'Physical Architecture'::'Physical Functions'::'Root Physical Function'.'Receive Athlete '.'outHelmut Motion'
                        to target ::> 'CDT_System Project'::'CDT_System'::'Physical Architecture'::'Physical Functions'::'Root Physical Function'.'Enable Monitoring'.'Enable Monitoring'.'inHelmut Motion' { 
                        attribute :>> isMulticast = false; 
                        attribute :>> kindOfRate = RateKind::Unspecified; 
                        attribute :>> isMultireceive = false; 
                        attribute :>> interfaceName = "Helmet Motion"; 
                         
                        ref :>> exchangedItems =  ('CDT_System Project'::'CDT_System'::'Physical Architecture'::'Data'::'Activity'); 
                    }  
                    interface 'b4f7ef4b-c36e-4150-bd3b-d844d16b02ba' : FunctionalExchange 
                        connect source ::> 'CDT_System Project'::'CDT_System'::'Physical Architecture'::'Physical Functions'::'Root Physical Function'.'Place on Helmet'.'outHead '
                        to target ::> 'CDT_System Project'::'CDT_System'::'Physical Architecture'::'Physical Functions'::'Root Physical Function'.'Receive Athlete '.'inHead ' { 
                        attribute :>> isMulticast = false; 
                        attribute :>> kindOfRate = RateKind::Unspecified; 
                        attribute :>> isMultireceive = false; 
                        attribute :>> interfaceName = "Head "; 
                         
                    }  
                    interface '23e5f028-b459-46de-b970-6d260ce6ca65' : FunctionalExchange 
                        connect source ::> 'CDT_System Project'::'CDT_System'::'Physical Architecture'::'Physical Functions'::'Root Physical Function'.'Data is Retrieved'.'Intitate Data Retrieval'.'Initiate Data Retrieve'.'outRecorded Data'
                        to target ::> 'CDT_System Project'::'CDT_System'::'Physical Architecture'::'Physical Functions'::'Root Physical Function'.'Data stored'.'Data Stored'.'inRecorded Data' { 
                        attribute :>> isMulticast = false; 
                        attribute :>> kindOfRate = RateKind::Unspecified; 
                        attribute :>> isMultireceive = false; 
                        attribute :>> interfaceName = "Recorded Data"; 
                         
                    }  
                    interface 'fb33a517-f686-437b-afcf-1bfaf8863b31' : FunctionalExchange 
                        connect source ::> 'CDT_System Project'::'CDT_System'::'Physical Architecture'::'Physical Functions'::'Root Physical Function'.'Data stored'.'Data is Presented'.'outStored Data '
                        to target ::> 'CDT_System Project'::'CDT_System'::'Physical Architecture'::'Physical Functions'::'Root Physical Function'.'Data can be reviewed'.'inStored Data ' { 
                        attribute :>> isMulticast = false; 
                        attribute :>> kindOfRate = RateKind::Unspecified; 
                        attribute :>> isMultireceive = false; 
                        attribute :>> interfaceName = "Stored Data "; 
                         
                    }  
                    interface '68e52c77-d9b5-4ca2-9857-40506d382b2a' : FunctionalExchange 
                        connect source ::> 'CDT_System Project'::'CDT_System'::'Physical Architecture'::'Physical Functions'::'Root Physical Function'.'Data can be reviewed'.'outInteraction 26'
                        to target ::> 'CDT_System Project'::'CDT_System'::'Physical Architecture'::'Physical Functions'::'Root Physical Function'.'Executes Policies'.'inInteraction 26' { 
                        attribute :>> isMulticast = false; 
                        attribute :>> kindOfRate = RateKind::Unspecified; 
                        attribute :>> isMultireceive = false; 
                        attribute :>> interfaceName = "Interaction 26"; 
                         
                    }  
                    interface 'a748da4c-426a-41d1-a0a6-75d444ba45ff' : FunctionalExchange 
                        connect source ::> 'CDT_System Project'::'CDT_System'::'Physical Architecture'::'Physical Functions'::'Root Physical Function'.'Aquire System'.'outSystem '
                        to target ::> 'CDT_System Project'::'CDT_System'::'Physical Architecture'::'Physical Functions'::'Root Physical Function'.'Established Concussion Policy'.'inSystem ' { 
                        attribute :>> isMulticast = false; 
                        attribute :>> kindOfRate = RateKind::Unspecified; 
                        attribute :>> isMultireceive = false; 
                        attribute :>> interfaceName = "System "; 
                         
                    }  
                    interface '9b1799b8-5252-4bff-b3be-6f12966886ea' : FunctionalExchange 
                        connect source ::> 'CDT_System Project'::'CDT_System'::'Physical Architecture'::'Physical Functions'::'Root Physical Function'.'Established Concussion Policy'.'outConcussion Policy'
                        to target ::> 'CDT_System Project'::'CDT_System'::'Physical Architecture'::'Physical Functions'::'Root Physical Function'.'Trainer Recieves Concussion Alert'.'inConcussion Policy' { 
                        attribute :>> isMulticast = false; 
                        attribute :>> kindOfRate = RateKind::Unspecified; 
                        attribute :>> isMultireceive = false; 
                        attribute :>> interfaceName = "Concussion Policy"; 
                         
                    }  
                    interface '7d222aa7-b806-4a69-9cab-674e9f1e0de0' : FunctionalExchange 
                        connect source ::> 'CDT_System Project'::'CDT_System'::'Physical Architecture'::'Physical Functions'::'Root Physical Function'.'Provide ID Information'.'outDevice ID '
                        to target ::> 'CDT_System Project'::'CDT_System'::'Physical Architecture'::'Physical Functions'::'Root Physical Function'.'Enable Secure Collection'.'inDevice ID ' { 
                        attribute :>> isMulticast = false; 
                        attribute :>> kindOfRate = RateKind::Unspecified; 
                        attribute :>> isMultireceive = false; 
                        attribute :>> interfaceName = "Device ID "; 
                         
                    }  
                    interface 'a8c90ff0-2958-40d5-988c-abcdfec9eb30' : FunctionalExchange 
                        connect source ::> 'CDT_System Project'::'CDT_System'::'Physical Architecture'::'Physical Functions'::'Root Physical Function'.'Executes Policies'.'outExecute Policy'
                        to target ::> 'CDT_System Project'::'CDT_System'::'Physical Architecture'::'Physical Functions'::'Root Physical Function'.'Generates Reports'.'Request Report to be sent'.'inExecute Policy' { 
                        attribute :>> isMulticast = false; 
                        attribute :>> kindOfRate = RateKind::Unspecified; 
                        attribute :>> isMultireceive = false; 
                        attribute :>> interfaceName = "Execute Policy"; 
                         
                    }  
                    interface 'f1f0f7a6-2ffc-4f52-9adb-75dad141f50c' : FunctionalExchange 
                        connect source ::> 'CDT_System Project'::'CDT_System'::'Physical Architecture'::'Physical Functions'::'Root Physical Function'.'Trainer Recieves Concussion Alert'.'outAlert'
                        to target ::> 'CDT_System Project'::'CDT_System'::'Physical Architecture'::'Physical Functions'::'Root Physical Function'.'Yield to Evaluation'.'inAlert' { 
                        attribute :>> isMulticast = false; 
                        attribute :>> kindOfRate = RateKind::Unspecified; 
                        attribute :>> isMultireceive = false; 
                        attribute :>> interfaceName = "Alert"; 
                         
                    }  
                    interface '0cb04311-e193-4748-b3dd-d9e448d795ff' : FunctionalExchange 
                        connect source ::> 'CDT_System Project'::'CDT_System'::'Physical Architecture'::'Physical Functions'::'Root Physical Function'.'Generates Reports'.'Generate Reports'.'outAthlete Report'
                        to target ::> 'CDT_System Project'::'CDT_System'::'Physical Architecture'::'Physical Functions'::'Root Physical Function'.'Report Received'.'inAthlete Report' { 
                        attribute :>> isMulticast = false; 
                        attribute :>> kindOfRate = RateKind::Unspecified; 
                        attribute :>> isMultireceive = false; 
                        attribute :>> interfaceName = "Athlete Report"; 
                         
                    }  
                    interface 'b88170f2-5332-4406-9d71-270e24df9b11' : FunctionalExchange 
                        connect source ::> 'CDT_System Project'::'CDT_System'::'Physical Architecture'::'Physical Functions'::'Root Physical Function'.'Enable Secure Collection'.'outSensor Ready'
                        to target ::> 'CDT_System Project'::'CDT_System'::'Physical Architecture'::'Physical Functions'::'Root Physical Function'.'Enable Monitoring'.'Enable Monitoring'.'inSensor Ready' { 
                        attribute :>> isMulticast = false; 
                        attribute :>> kindOfRate = RateKind::Unspecified; 
                        attribute :>> isMultireceive = false; 
                        attribute :>> interfaceName = "Sensor Ready"; 
                         
                    }  
                    interface '06a84b77-2a20-41cc-9152-8af91456e9f7' : FunctionalExchange 
                        connect source ::> 'CDT_System Project'::'CDT_System'::'Physical Architecture'::'Physical Functions'::'Root Physical Function'.'Enable Monitoring'.'Enable Indicated'.'outEnable Signal'
                        to target ::> 'CDT_System Project'::'CDT_System'::'Physical Architecture'::'Physical Functions'::'Root Physical Function'.'Recieve Enabled Signal from Athelete Helmet'.'inEnable Signal' { 
                        attribute :>> isMulticast = false; 
                        attribute :>> kindOfRate = RateKind::Unspecified; 
                        attribute :>> isMultireceive = false; 
                        attribute :>> interfaceName = "Enable Signal"; 
                         
                    }  
                    interface '7cae195c-34e2-448e-853e-b8945137813d' : FunctionalExchange 
                        connect source ::> 'CDT_System Project'::'CDT_System'::'Physical Architecture'::'Physical Functions'::'Root Physical Function'.'Insert ID into Sensing Device'.'outReady to put on Helmut'
                        to target ::> 'CDT_System Project'::'CDT_System'::'Physical Architecture'::'Physical Functions'::'Root Physical Function'.'Place on Helmet'.'inReady to put on Helmut' { 
                        attribute :>> isMulticast = false; 
                        attribute :>> kindOfRate = RateKind::Unspecified; 
                        attribute :>> isMultireceive = false; 
                        attribute :>> interfaceName = "Ready to put on Helmet"; 
                         
                    }  
                    interface '12ebf309-1bfb-49d3-b323-3f518edb7c44' : FunctionalExchange 
                        connect source ::> 'CDT_System Project'::'CDT_System'::'Physical Architecture'::'Physical Functions'::'Root Physical Function'.'Generates Reports'.'Generate Reports'.'outInstition Report'
                        to target ::> 'CDT_System Project'::'CDT_System'::'Physical Architecture'::'Physical Functions'::'Root Physical Function'.'Report Received'.'inInstition Report' { 
                        attribute :>> isMulticast = false; 
                        attribute :>> kindOfRate = RateKind::Unspecified; 
                        attribute :>> isMultireceive = false; 
                        attribute :>> interfaceName = "Instition Report"; 
                         
                    }  
                    interface 'f0af47e2-b70f-4aad-b565-346bf3cfa078' : FunctionalExchange 
                        connect source ::> 'CDT_System Project'::'CDT_System'::'Physical Architecture'::'Physical Functions'::'Root Physical Function'.'Generates Reports'.'Generate Reports'.'outParen Report'
                        to target ::> 'CDT_System Project'::'CDT_System'::'Physical Architecture'::'Physical Functions'::'Root Physical Function'.'Report received'.'inParen Report' { 
                        attribute :>> isMulticast = false; 
                        attribute :>> kindOfRate = RateKind::Unspecified; 
                        attribute :>> isMultireceive = false; 
                        attribute :>> interfaceName = "Paren Report"; 
                         
                    }  
                    interface '475ff723-d6b5-4cd3-90eb-90c3ab68be89' : FunctionalExchange 
                        connect source ::> 'CDT_System Project'::'CDT_System'::'Physical Architecture'::'Physical Functions'::'Root Physical Function'.'Yield to Evaluation'.'outEvaluation'
                        to target ::> 'CDT_System Project'::'CDT_System'::'Physical Architecture'::'Physical Functions'::'Root Physical Function'.'Data is Retrieved'.'Intitate Data Retrieval'.'Evaluate Player'.'inEvaluation' { 
                        attribute :>> isMulticast = false; 
                        attribute :>> kindOfRate = RateKind::Unspecified; 
                        attribute :>> isMultireceive = false; 
                        attribute :>> interfaceName = "Evaluation"; 
                         
                    }  
                    interface '497aee27-9576-4bc0-bf81-4968901d568b' : FunctionalExchange 
                        connect source ::> 'CDT_System Project'::'CDT_System'::'Physical Architecture'::'Physical Functions'::'Root Physical Function'.'Device alerts possible Concussion'.'Alert the Training'.'outConcussion Alert to Trainer'
                        to target ::> 'CDT_System Project'::'CDT_System'::'Physical Architecture'::'Physical Functions'::'Root Physical Function'.'Trainer Recieves Concussion Alert'.'inConcussion Alert to Trainer' { 
                        attribute :>> isMulticast = false; 
                        attribute :>> kindOfRate = RateKind::Unspecified; 
                        attribute :>> isMultireceive = false; 
                        attribute :>> interfaceName = "Concussion Alert to Trainer"; 
                         
                    }  
                    interface 'f3a9de66-ff37-4ea1-8782-8e3a7b10dbef' : FunctionalExchange 
                        connect source ::> 'CDT_System Project'::'CDT_System'::'Physical Architecture'::'Physical Functions'::'Root Physical Function'.'Trainer Recieves Concussion Alert'.'FOP 2'
                        to target ::> 'CDT_System Project'::'CDT_System'::'Physical Architecture'::'Physical Functions'::'Root Physical Function'.'Data is Retrieved'.'Intitate Data Retrieval'.'Evaluate Player'.'FIP 2' { 
                        attribute :>> isMulticast = false; 
                        attribute :>> kindOfRate = RateKind::Unspecified; 
                        attribute :>> isMultireceive = false; 
                        attribute :>> interfaceName = "Player ID"; 
                         
                    }  
                    interface '8a61ea1c-4cc3-4fd2-b046-0ff52f5d6433' : FunctionalExchange 
                        connect source ::> 'CDT_System Project'::'CDT_System'::'Physical Architecture'::'Physical Functions'::'Root Physical Function'.'Store Profile'.'Store Profile'.'FOP 1'
                        to target ::> 'CDT_System Project'::'CDT_System'::'Physical Architecture'::'Physical Functions'::'Root Physical Function'.'Create Unique IDs for Athlete'.'Create ID'.'FIP 2' { 
                        attribute :>> isMulticast = false; 
                        attribute :>> kindOfRate = RateKind::Unspecified; 
                        attribute :>> isMultireceive = false; 
                        attribute :>> interfaceName = "Profile Data"; 
                         
                    }  
                    interface '69140741-68f0-453d-858b-b6395ac5cdb0' : FunctionalExchange 
                        connect source ::> 'CDT_System Project'::'CDT_System'::'Physical Architecture'::'Physical Functions'::'Root Physical Function'.'Device alerts possible Concussion'.'Send message'.'FOP 1'
                        to target ::> 'CDT_System Project'::'CDT_System'::'Physical Architecture'::'Physical Functions'::'Root Physical Function'.'Transfer Uplink Data'.'From sensors' { 
                        attribute :>> isMulticast = false; 
                        attribute :>> kindOfRate = RateKind::Unspecified; 
                        attribute :>> isMultireceive = false; 
                        attribute :>> interfaceName = "Concussion Message"; 
                         
                        ref :>> exchangedItems =  ('CDT_System Project'::'CDT_System'::'Physical Architecture'::'Data'::'Concussion Data'); 
                    }  
                    interface '47c4e8e5-b091-4e08-a377-9a091f71beac' : FunctionalExchange 
                        connect source ::> 'CDT_System Project'::'CDT_System'::'Physical Architecture'::'Physical Functions'::'Root Physical Function'.'Transfer Uplink Data'.'To Cloud Console'
                        to target ::> 'CDT_System Project'::'CDT_System'::'Physical Architecture'::'Physical Functions'::'Root Physical Function'.'Device alerts possible Concussion'.'Record the Concussion'.'FIP 1' { 
                        attribute :>> isMulticast = false; 
                        attribute :>> kindOfRate = RateKind::Unspecified; 
                        attribute :>> isMultireceive = false; 
                        attribute :>> interfaceName = "Concussion Message"; 
                         
                    }  
                    interface '512d646a-097e-4801-9a13-cd5ecc3487dc' : FunctionalExchange 
                        connect source ::> 'CDT_System Project'::'CDT_System'::'Physical Architecture'::'Physical Functions'::'Root Physical Function'.'Enable Monitoring'.'Enable Monitoring'.'FOP 1'
                        to target ::> 'CDT_System Project'::'CDT_System'::'Physical Architecture'::'Physical Functions'::'Root Physical Function'.'Transfer Uplink Data'.'From sensors' { 
                        attribute :>> isMulticast = false; 
                        attribute :>> kindOfRate = RateKind::Unspecified; 
                        attribute :>> isMultireceive = false; 
                        attribute :>> interfaceName = "Enable Signal"; 
                         
                    }  
                    interface '33c7de34-5819-4162-a02e-b2d39af813fa' : FunctionalExchange 
                        connect source ::> 'CDT_System Project'::'CDT_System'::'Physical Architecture'::'Physical Functions'::'Root Physical Function'.'Transfer Uplink Data'.'To Cloud Console'
                        to target ::> 'CDT_System Project'::'CDT_System'::'Physical Architecture'::'Physical Functions'::'Root Physical Function'.'Enable Monitoring'.'Enable Recored'.'FIP 1' { 
                        attribute :>> isMulticast = false; 
                        attribute :>> kindOfRate = RateKind::Unspecified; 
                        attribute :>> isMultireceive = false; 
                        attribute :>> interfaceName = "Enable"; 
                         
                    }  
                    interface '7f23244f-9558-4fef-b8bf-fb3cb5e42ddc' : FunctionalExchange 
                        connect source ::> 'CDT_System Project'::'CDT_System'::'Physical Architecture'::'Physical Functions'::'Root Physical Function'.'Removes Helmut'.'FOP 1'
                        to target ::> 'CDT_System Project'::'CDT_System'::'Physical Architecture'::'Physical Functions'::'Root Physical Function'.'Exit Athlete'.'FIP 1' { 
                        attribute :>> isMulticast = false; 
                        attribute :>> kindOfRate = RateKind::Unspecified; 
                        attribute :>> isMultireceive = false; 
                        attribute :>> interfaceName = "Head"; 
                    }  
                    interface 'a367259a-8c5d-4679-a322-ee0fa1ab9cb1' : FunctionalExchange 
                        connect source ::> 'CDT_System Project'::'CDT_System'::'Physical Architecture'::'Physical Functions'::'Root Physical Function'.'Exit Athlete'.'FOP 1'
                        to target ::> 'CDT_System Project'::'CDT_System'::'Physical Architecture'::'Physical Functions'::'Root Physical Function'.'Disable Monitoring'.'FIP 1' { 
                        attribute :>> isMulticast = false; 
                        attribute :>> kindOfRate = RateKind::Unspecified; 
                        attribute :>> isMultireceive = false; 
                        attribute :>> interfaceName = "Activity"; 
                    }  
                    interface '95185f6a-8c82-4db9-a48c-b51e468be017' : FunctionalExchange 
                        connect source ::> 'CDT_System Project'::'CDT_System'::'Physical Architecture'::'Physical Functions'::'Root Physical Function'.'Remove ID'.'FOP 1'
                        to target ::> 'CDT_System Project'::'CDT_System'::'Physical Architecture'::'Physical Functions'::'Root Physical Function'.'Disable Secure Collection'.'FIP 1' { 
                        attribute :>> isMulticast = false; 
                        attribute :>> kindOfRate = RateKind::Unspecified; 
                        attribute :>> isMultireceive = false; 
                        attribute :>> interfaceName = "ID Removed"; 
                    }  
                    interface '9ef1c681-b828-4413-96e1-48af3a681b0d' : FunctionalExchange 
                        connect source ::> 'CDT_System Project'::'CDT_System'::'Physical Architecture'::'Physical Functions'::'Root Physical Function'.'Disable Secure Collection'.'FOP 1'
                        to target ::> 'CDT_System Project'::'CDT_System'::'Physical Architecture'::'Physical Functions'::'Root Physical Function'.'Disable Monitoring'.'FIP 2' { 
                        attribute :>> isMulticast = false; 
                        attribute :>> kindOfRate = RateKind::Unspecified; 
                        attribute :>> isMultireceive = false; 
                        attribute :>> interfaceName = "Disable"; 
                    }  
                     
                    ref :>> ownedFunctions =  ('CDT_System Project'::'CDT_System'::'Physical Architecture'::'Physical Functions'::'Root Physical Function'.'Enable Monitoring',
                    'CDT_System Project'::'CDT_System'::'Physical Architecture'::'Physical Functions'::'Root Physical Function'.'Recieve Enabled Signal from Athelete Helmet',
                    'CDT_System Project'::'CDT_System'::'Physical Architecture'::'Physical Functions'::'Root Physical Function'.'Data stored',
                    'CDT_System Project'::'CDT_System'::'Physical Architecture'::'Physical Functions'::'Root Physical Function'.'Data can be reviewed',
                    'CDT_System Project'::'CDT_System'::'Physical Architecture'::'Physical Functions'::'Root Physical Function'.'Report Received',
                    'CDT_System Project'::'CDT_System'::'Physical Architecture'::'Physical Functions'::'Root Physical Function'.'Report Received',
                    'CDT_System Project'::'CDT_System'::'Physical Architecture'::'Physical Functions'::'Root Physical Function'.'Report received',
                    'CDT_System Project'::'CDT_System'::'Physical Architecture'::'Physical Functions'::'Root Physical Function'.'Executes Policies',
                    'CDT_System Project'::'CDT_System'::'Physical Architecture'::'Physical Functions'::'Root Physical Function'.'Established Concussion Policy',
                    'CDT_System Project'::'CDT_System'::'Physical Architecture'::'Physical Functions'::'Root Physical Function'.'Generates Reports',
                    'CDT_System Project'::'CDT_System'::'Physical Architecture'::'Physical Functions'::'Root Physical Function'.'Helmet Receives a Hit',
                    'CDT_System Project'::'CDT_System'::'Physical Architecture'::'Physical Functions'::'Root Physical Function'.'Enable Secure Collection',
                    'CDT_System Project'::'CDT_System'::'Physical Architecture'::'Physical Functions'::'Root Physical Function'.'Place on Helmet',
                    'CDT_System Project'::'CDT_System'::'Physical Architecture'::'Physical Functions'::'Root Physical Function'.'Device',
                    'CDT_System Project'::'CDT_System'::'Physical Architecture'::'Physical Functions'::'Root Physical Function'.'Provide ID Information',
                    'CDT_System Project'::'CDT_System'::'Physical Architecture'::'Physical Functions'::'Root Physical Function'.'Athlete Particpates in Activity',
                    'CDT_System Project'::'CDT_System'::'Physical Architecture'::'Physical Functions'::'Root Physical Function'.'Yield to Evaluation',
                    'CDT_System Project'::'CDT_System'::'Physical Architecture'::'Physical Functions'::'Root Physical Function'.'Receive Athlete ',
                    'CDT_System Project'::'CDT_System'::'Physical Architecture'::'Physical Functions'::'Root Physical Function'.'Data is Retrieved',
                    'CDT_System Project'::'CDT_System'::'Physical Architecture'::'Physical Functions'::'Root Physical Function'.'Device Detects Activity',
                    'CDT_System Project'::'CDT_System'::'Physical Architecture'::'Physical Functions'::'Root Physical Function'.'Aquire System',
                    'CDT_System Project'::'CDT_System'::'Physical Architecture'::'Physical Functions'::'Root Physical Function'.'Create profiles for Athletes',
                    'CDT_System Project'::'CDT_System'::'Physical Architecture'::'Physical Functions'::'Root Physical Function'.'Create Unique IDs for Athlete',
                    'CDT_System Project'::'CDT_System'::'Physical Architecture'::'Physical Functions'::'Root Physical Function'.'Provide Data for Profile',
                    'CDT_System Project'::'CDT_System'::'Physical Architecture'::'Physical Functions'::'Root Physical Function'.'Recieve ID',
                    'CDT_System Project'::'CDT_System'::'Physical Architecture'::'Physical Functions'::'Root Physical Function'.'Store Profile',
                    'CDT_System Project'::'CDT_System'::'Physical Architecture'::'Physical Functions'::'Root Physical Function'.'Create Unique IDs',
                    'CDT_System Project'::'CDT_System'::'Physical Architecture'::'Physical Functions'::'Root Physical Function'.'Provide ID to Athlete',
                    'CDT_System Project'::'CDT_System'::'Physical Architecture'::'Physical Functions'::'Root Physical Function'.'Assemble System Components',
                    'CDT_System Project'::'CDT_System'::'Physical Architecture'::'Physical Functions'::'Root Physical Function'.'Provide access to helmut mounting',
                    'CDT_System Project'::'CDT_System'::'Physical Architecture'::'Physical Functions'::'Root Physical Function'.'Provide access to sensing device mounting',
                    'CDT_System Project'::'CDT_System'::'Physical Architecture'::'Physical Functions'::'Root Physical Function'.'Prep the device for use',
                    'CDT_System Project'::'CDT_System'::'Physical Architecture'::'Physical Functions'::'Root Physical Function'.'Insert ID into Sensing Device',
                    'CDT_System Project'::'CDT_System'::'Physical Architecture'::'Physical Functions'::'Root Physical Function'.'Recieve ID',
                    'CDT_System Project'::'CDT_System'::'Physical Architecture'::'Physical Functions'::'Root Physical Function'.'Device alerts possible Concussion',
                    'CDT_System Project'::'CDT_System'::'Physical Architecture'::'Physical Functions'::'Root Physical Function'.'Trainer Recieves Concussion Alert',
                    'CDT_System Project'::'CDT_System'::'Physical Architecture'::'Physical Functions'::'Root Physical Function'.'Transfer Downlink Data',
                    'CDT_System Project'::'CDT_System'::'Physical Architecture'::'Physical Functions'::'Root Physical Function'.'Transfer Uplink Data',
                    'CDT_System Project'::'CDT_System'::'Physical Architecture'::'Physical Functions'::'Root Physical Function'.'Transfer Uplink Data',
                    'CDT_System Project'::'CDT_System'::'Physical Architecture'::'Physical Functions'::'Root Physical Function'.'Transfer Downlink Data',
                    'CDT_System Project'::'CDT_System'::'Physical Architecture'::'Physical Functions'::'Root Physical Function'.'Removes Helmut',
                    'CDT_System Project'::'CDT_System'::'Physical Architecture'::'Physical Functions'::'Root Physical Function'.'Exit Athlete',
                    'CDT_System Project'::'CDT_System'::'Physical Architecture'::'Physical Functions'::'Root Physical Function'.'Disable Monitoring',
                    'CDT_System Project'::'CDT_System'::'Physical Architecture'::'Physical Functions'::'Root Physical Function'.'Remove ID',
                    'CDT_System Project'::'CDT_System'::'Physical Architecture'::'Physical Functions'::'Root Physical Function'.'Disable Secure Collection'); 
                     
                    ref :>> ownedFunctionalExchanges =  ('CDT_System Project'::'CDT_System'::'Physical Architecture'::'Physical Functions'::'Root Physical Function'.'9cf0b319-b000-4762-a282-3c1bc1f8d9f2',
                    'CDT_System Project'::'CDT_System'::'Physical Architecture'::'Physical Functions'::'Root Physical Function'.'9d36dfac-6872-4444-b1bd-2a76b69f97ad',
                    'CDT_System Project'::'CDT_System'::'Physical Architecture'::'Physical Functions'::'Root Physical Function'.'a217c874-3cbb-450a-923b-577fed855515',
                    'CDT_System Project'::'CDT_System'::'Physical Architecture'::'Physical Functions'::'Root Physical Function'.'51151e46-28af-4063-ad37-f00316ee0123',
                    'CDT_System Project'::'CDT_System'::'Physical Architecture'::'Physical Functions'::'Root Physical Function'.'491b2553-4a8f-4b59-9814-3afb66dd3774',
                    'CDT_System Project'::'CDT_System'::'Physical Architecture'::'Physical Functions'::'Root Physical Function'.'e665875a-d1bc-4524-a7ec-836e28b52f86',
                    'CDT_System Project'::'CDT_System'::'Physical Architecture'::'Physical Functions'::'Root Physical Function'.'7def9910-a949-4522-850b-91b33367ae40',
                    'CDT_System Project'::'CDT_System'::'Physical Architecture'::'Physical Functions'::'Root Physical Function'.'17084ce1-140b-4e28-9fdf-600155068998',
                    'CDT_System Project'::'CDT_System'::'Physical Architecture'::'Physical Functions'::'Root Physical Function'.'ac3ab92b-994d-4d14-9677-e9de084fb231',
                    'CDT_System Project'::'CDT_System'::'Physical Architecture'::'Physical Functions'::'Root Physical Function'.'95336049-dc3c-407c-b6a4-0c7f3880f37d',
                    'CDT_System Project'::'CDT_System'::'Physical Architecture'::'Physical Functions'::'Root Physical Function'.'ed81e988-0a73-487a-8ad8-3aecdc70dd30',
                    'CDT_System Project'::'CDT_System'::'Physical Architecture'::'Physical Functions'::'Root Physical Function'.'33df8ee7-ec53-401b-ad2d-a4b5ed379d65',
                    'CDT_System Project'::'CDT_System'::'Physical Architecture'::'Physical Functions'::'Root Physical Function'.'22090920-c6f9-46bd-98bf-3d5e170f291f',
                    'CDT_System Project'::'CDT_System'::'Physical Architecture'::'Physical Functions'::'Root Physical Function'.'da635154-d82f-4121-91dc-7a2c0516e106',
                    'CDT_System Project'::'CDT_System'::'Physical Architecture'::'Physical Functions'::'Root Physical Function'.'08b5ae87-3ed6-4398-a929-d9722caebf91',
                    'CDT_System Project'::'CDT_System'::'Physical Architecture'::'Physical Functions'::'Root Physical Function'.'148b6701-406e-4365-966a-60959c61b469',
                    'CDT_System Project'::'CDT_System'::'Physical Architecture'::'Physical Functions'::'Root Physical Function'.'ba2b6ed1-f6cd-4a3b-98b1-83362c975fe3',
                    'CDT_System Project'::'CDT_System'::'Physical Architecture'::'Physical Functions'::'Root Physical Function'.'7ce6b399-9ac1-4a1b-b0d8-408b5659bcd3',
                    'CDT_System Project'::'CDT_System'::'Physical Architecture'::'Physical Functions'::'Root Physical Function'.'7b17df23-af62-44ed-acba-7747c33550e5',
                    'CDT_System Project'::'CDT_System'::'Physical Architecture'::'Physical Functions'::'Root Physical Function'.'b4f7ef4b-c36e-4150-bd3b-d844d16b02ba',
                    'CDT_System Project'::'CDT_System'::'Physical Architecture'::'Physical Functions'::'Root Physical Function'.'23e5f028-b459-46de-b970-6d260ce6ca65',
                    'CDT_System Project'::'CDT_System'::'Physical Architecture'::'Physical Functions'::'Root Physical Function'.'fb33a517-f686-437b-afcf-1bfaf8863b31',
                    'CDT_System Project'::'CDT_System'::'Physical Architecture'::'Physical Functions'::'Root Physical Function'.'68e52c77-d9b5-4ca2-9857-40506d382b2a',
                    'CDT_System Project'::'CDT_System'::'Physical Architecture'::'Physical Functions'::'Root Physical Function'.'a748da4c-426a-41d1-a0a6-75d444ba45ff',
                    'CDT_System Project'::'CDT_System'::'Physical Architecture'::'Physical Functions'::'Root Physical Function'.'9b1799b8-5252-4bff-b3be-6f12966886ea',
                    'CDT_System Project'::'CDT_System'::'Physical Architecture'::'Physical Functions'::'Root Physical Function'.'7d222aa7-b806-4a69-9cab-674e9f1e0de0',
                    'CDT_System Project'::'CDT_System'::'Physical Architecture'::'Physical Functions'::'Root Physical Function'.'a8c90ff0-2958-40d5-988c-abcdfec9eb30',
                    'CDT_System Project'::'CDT_System'::'Physical Architecture'::'Physical Functions'::'Root Physical Function'.'f1f0f7a6-2ffc-4f52-9adb-75dad141f50c',
                    'CDT_System Project'::'CDT_System'::'Physical Architecture'::'Physical Functions'::'Root Physical Function'.'0cb04311-e193-4748-b3dd-d9e448d795ff',
                    'CDT_System Project'::'CDT_System'::'Physical Architecture'::'Physical Functions'::'Root Physical Function'.'b88170f2-5332-4406-9d71-270e24df9b11',
                    'CDT_System Project'::'CDT_System'::'Physical Architecture'::'Physical Functions'::'Root Physical Function'.'06a84b77-2a20-41cc-9152-8af91456e9f7',
                    'CDT_System Project'::'CDT_System'::'Physical Architecture'::'Physical Functions'::'Root Physical Function'.'7cae195c-34e2-448e-853e-b8945137813d',
                    'CDT_System Project'::'CDT_System'::'Physical Architecture'::'Physical Functions'::'Root Physical Function'.'12ebf309-1bfb-49d3-b323-3f518edb7c44',
                    'CDT_System Project'::'CDT_System'::'Physical Architecture'::'Physical Functions'::'Root Physical Function'.'f0af47e2-b70f-4aad-b565-346bf3cfa078',
                    'CDT_System Project'::'CDT_System'::'Physical Architecture'::'Physical Functions'::'Root Physical Function'.'475ff723-d6b5-4cd3-90eb-90c3ab68be89',
                    'CDT_System Project'::'CDT_System'::'Physical Architecture'::'Physical Functions'::'Root Physical Function'.'497aee27-9576-4bc0-bf81-4968901d568b',
                    'CDT_System Project'::'CDT_System'::'Physical Architecture'::'Physical Functions'::'Root Physical Function'.'f3a9de66-ff37-4ea1-8782-8e3a7b10dbef',
                    'CDT_System Project'::'CDT_System'::'Physical Architecture'::'Physical Functions'::'Root Physical Function'.'8a61ea1c-4cc3-4fd2-b046-0ff52f5d6433',
                    'CDT_System Project'::'CDT_System'::'Physical Architecture'::'Physical Functions'::'Root Physical Function'.'69140741-68f0-453d-858b-b6395ac5cdb0',
                    'CDT_System Project'::'CDT_System'::'Physical Architecture'::'Physical Functions'::'Root Physical Function'.'47c4e8e5-b091-4e08-a377-9a091f71beac',
                    'CDT_System Project'::'CDT_System'::'Physical Architecture'::'Physical Functions'::'Root Physical Function'.'512d646a-097e-4801-9a13-cd5ecc3487dc',
                    'CDT_System Project'::'CDT_System'::'Physical Architecture'::'Physical Functions'::'Root Physical Function'.'33c7de34-5819-4162-a02e-b2d39af813fa',
                    'CDT_System Project'::'CDT_System'::'Physical Architecture'::'Physical Functions'::'Root Physical Function'.'7f23244f-9558-4fef-b8bf-fb3cb5e42ddc',
                    'CDT_System Project'::'CDT_System'::'Physical Architecture'::'Physical Functions'::'Root Physical Function'.'a367259a-8c5d-4679-a322-ee0fa1ab9cb1',
                    'CDT_System Project'::'CDT_System'::'Physical Architecture'::'Physical Functions'::'Root Physical Function'.'95185f6a-8c82-4db9-a48c-b51e468be017',
                    'CDT_System Project'::'CDT_System'::'Physical Architecture'::'Physical Functions'::'Root Physical Function'.'9ef1c681-b828-4413-96e1-48af3a681b0d'); 
                }  
            } 
            package  'Interfaces' {
                @PackageMeta {
                    type = "InterfacePkg";
                } 
                item 'LORA ' : InterfaceItem  { 
                    attribute :>> isStructural = true; 
                    attribute :>> isAbstract = false; 
                    attribute :>> isFinal = false; 
                    allocation '0f5e8ee3-e0bd-4f18-bfa2-d34dd517834c' : ExchangeItemAllocation
                        allocate allocatedItem ::> 'CDT_System Project'::'CDT_System'::'Physical Architecture'::'Data'::'Concussion Data'
                        to allocatingInterface ::> 'CDT_System Project'::'CDT_System'::'Physical Architecture'::'Interfaces'::'LORA '; 
                     
                    ref :>> ownedExchangeItemAllocations =  ('CDT_System Project'::'CDT_System'::'Physical Architecture'::'Interfaces'::'LORA '.'0f5e8ee3-e0bd-4f18-bfa2-d34dd517834c'); 
                }  
                item 'Helmut to Sensor' : InterfaceItem  { 
                    attribute :>> isStructural = true; 
                    attribute :>> isAbstract = false; 
                    attribute :>> isFinal = false; 
                    allocation '68ed8a7f-9c83-464e-a4ec-95847fe577d1' : ExchangeItemAllocation
                        allocate allocatedItem ::> 'CDT_System Project'::'CDT_System'::'Physical Architecture'::'Data'::'Activity'
                        to allocatingInterface ::> 'CDT_System Project'::'CDT_System'::'Physical Architecture'::'Interfaces'::'Helmut to Sensor'; 
                     
                    ref :>> ownedExchangeItemAllocations =  ('CDT_System Project'::'CDT_System'::'Physical Architecture'::'Interfaces'::'Helmut to Sensor'.'68ed8a7f-9c83-464e-a4ec-95847fe577d1'); 
                }  
            } 
            package  'Capabilities' {
                @PackageMeta {
                    type = "CapabilityRealizationPkg";
                } 
                use case 'Maintain Device' : CapabilityRealization { 
                    ref action 'acd2d1fb-56de-4fd5-9eb2-4449e1ddce2f' = 'CDT_System Project'::'CDT_System'::'Physical Architecture'::'Physical Functions'::'Root Physical Function'.'Maintain'; 
                     
                     
                }  
                use case 'Aquire Device' : CapabilityRealization { 
                    ref action 'bcc6fb8c-9cb1-42f7-ac3d-4a1fd759f22d' = 'CDT_System Project'::'CDT_System'::'Physical Architecture'::'Physical Functions'::'Root Physical Function'.'Acquire Device'; 
                     
                     
                }  
                use case 'Activate Detection' : CapabilityRealization { 
                    ref action '9c6abd0b-1a5c-4628-9d2e-b0152a5b5229' = 'CDT_System Project'::'CDT_System'::'Physical Architecture'::'Physical Functions'::'Root Physical Function'.'Activate Detection Device'; 
                     
                     
                }  
                use case 'Download Data' : CapabilityRealization { 
                    ref action '0bab7467-6cbf-470a-afe2-4c5dbe0a6999' = 'CDT_System Project'::'CDT_System'::'Physical Architecture'::'Physical Functions'::'Root Physical Function'.'Download Data'; 
                     
                     
                }  
                use case 'Detect Concussion' : CapabilityRealization { 
                    ref action '97ce8f2c-dd2a-4250-8d7e-5113e3ee1593' = 'CDT_System Project'::'CDT_System'::'Physical Architecture'::'Physical Functions'::'Root Physical Function'.'Athlete Particpates in Activity'; 
                    ref action '38960b9d-4211-4dc0-8b9c-289dd6d5f4be' = 'CDT_System Project'::'CDT_System'::'Physical Architecture'::'Physical Functions'::'Root Physical Function'.'Helmet Receives a Hit'; 
                    ref action 'f6cf24d7-9849-463d-808e-411925bf7dcb' = 'CDT_System Project'::'CDT_System'::'Physical Architecture'::'Physical Functions'::'Root Physical Function'.'Device Detects Activity'; 
                    ref action '84eeb5b4-a89c-41ad-8d19-105509e0a569' = 'CDT_System Project'::'CDT_System'::'Physical Architecture'::'Physical Functions'::'Root Physical Function'.'Device alerts possible Concussion'; 
                    ref action 'b72cc956-ee49-4326-8be4-1179657f9a06' = 'CDT_System Project'::'CDT_System'::'Physical Architecture'::'Physical Functions'::'Root Physical Function'.'Data is Retrieved'; 
                    ref action '469945df-f99f-486f-baca-8219b26d2d59' = 'CDT_System Project'::'CDT_System'::'Physical Architecture'::'Physical Functions'::'Root Physical Function'.'Trainer Recieves Concussion Alert'; 
                    ref action 'edc304ae-61a0-4ec6-930a-7b332065b1fd' = 'CDT_System Project'::'CDT_System'::'Physical Architecture'::'Physical Functions'::'Root Physical Function'.'Detect Concussion'; 
                     
                     
                     
                }  
            } 
            package  'Structure' {
                @PackageMeta {
                    type = "PhysicalComponentPkg";
                } 
                part 'Physical System' : PhysicalComponent { 
                    attribute :>> nature = PhysicalComponentNature::UNSET; 
                    attribute :>> kind = PhysicalComponentKind::UNSET; 
                    attribute :>> isAbstract = false; 
                    attribute :>> isActor = false; 
                    attribute :>> isHuman = false; 
                    allocation 'ce9718b6-2b95-4b58-8ff7-73e1ba0ca0cb' : ComponentFunctionalAllocation
                        allocate function ::> 'CDT_System Project'::'CDT_System'::'Physical Architecture'::'Physical Functions'::'Root Physical Function'.'Device'
                        to component ::> 'CDT_System Project'::'CDT_System'::'Physical Architecture'::'Structure'::'Physical System';
                    perform 'CDT_System Project'::'CDT_System'::'Physical Architecture'::'Physical Functions'::'Root Physical Function'.'Device' ; 
                    interface 'a13d93ff-839d-46f2-a7fc-fed2b173cf6f' : PhysicalLink 
                        connect sourcePhysicalPort ::> 'CDT_System Project'::'CDT_System'::'Physical Architecture'::'Structure'::'Physical System'.'LORAWAN Gateway'.'To LORA Nodes'
                        to targetPhysicalPort ::> 'CDT_System Project'::'CDT_System'::'Physical Architecture'::'Structure'::'Physical System'.'Helmet'.'Sensor'.'PP 2' {
                        attribute :>> interfaceName = "LORA"; 
                        attribute 'Physical Properties' : PropertyValueGroup { 
                            attribute 'Maximum Distance (m)' : StringPropertyValue  = '300.0';  
                            attribute 'Standard' : StringPropertyValue  = 'ISO/IEC10725';  
                            ref :>> ownedPropertyValues =  ('CDT_System Project'::'CDT_System'::'Physical Architecture'::'Structure'::'Physical System'.'a13d93ff-839d-46f2-a7fc-fed2b173cf6f'.'Physical Properties'.'Maximum Distance (m)',
                            'CDT_System Project'::'CDT_System'::'Physical Architecture'::'Structure'::'Physical System'.'a13d93ff-839d-46f2-a7fc-fed2b173cf6f'.'Physical Properties'.'Standard'); 
                        }  
                         
                        ref :>> ownedPropertyValueGroups =  ('CDT_System Project'::'CDT_System'::'Physical Architecture'::'Structure'::'Physical System'.'a13d93ff-839d-46f2-a7fc-fed2b173cf6f'.'Physical Properties'); 
                        ref :>> appliedPropertyValueGroups =  ('CDT_System Project'::'CDT_System'::'Physical Architecture'::'Structure'::'Physical System'.'a13d93ff-839d-46f2-a7fc-fed2b173cf6f'.'Physical Properties'); 
                    }  
                    interface 'e8dd3f9a-3354-4942-b6ce-5c00cb4e940c' : PhysicalLink 
                        connect sourcePhysicalPort ::> 'CDT_System Project'::'CDT_System'::'Physical Architecture'::'Structure'::'Physical System'.'Router'.'To WIFI LORA'
                        to targetPhysicalPort ::> 'CDT_System Project'::'CDT_System'::'Physical Architecture'::'Structure'::'Physical System'.'LORAWAN Gateway'.'To WIFI' {
                        attribute :>> interfaceName = "WIFI"; 
                    }  
                    interface '2e92a680-2f2c-4680-83b7-a270ff0e03ec' : PhysicalLink 
                        connect sourcePhysicalPort ::> 'CDT_System Project'::'CDT_System'::'Physical Architecture'::'Structure'::'Physical System'.'IPAD'.'PP 1'
                        to targetPhysicalPort ::> 'CDT_System Project'::'CDT_System'::'Physical Architecture'::'Structure'::'Physical System'.'Router'.'To Local Network CAT 5' {
                        attribute :>> interfaceName = "WIFI"; 
                    }  
                    interface '5d95547a-c398-4329-bb3e-6d9fa601fd2b' : PhysicalLink 
                        connect sourcePhysicalPort ::> 'CDT_System Project'::'CDT_System'::'Physical Architecture'::'Structure'::'Physical System'.'ISP'.'To Cloud'
                        to targetPhysicalPort ::> 'CDT_System Project'::'CDT_System'::'Physical Architecture'::'Structure'::'Physical System'.'Cloud Server'.'PP 1' {
                        attribute :>> interfaceName = "Internet"; 
                    }  
                    interface 'cdbb2a10-dc56-4086-b54e-fa39b3643bc7' : PhysicalLink 
                        connect sourcePhysicalPort ::> 'CDT_System Project'::'CDT_System'::'Physical Architecture'::'Structure'::'Physical System'.'Cellular Network ISP'.'PP 1'
                        to targetPhysicalPort ::> 'CDT_System Project'::'CDT_System'::'Physical Architecture'::'Structure'::'Physical System'.'Cloud Server'.'PP 2' {
                        attribute :>> interfaceName = "Internet"; 
                    }  
                    interface '8d99de49-a60c-4dde-9221-99cc3442109c' : PhysicalLink 
                        connect sourcePhysicalPort ::> 'CDT_System Project'::'CDT_System'::'Physical Architecture'::'Structure'::'Physical System'.'Cellular Network ISP'.'PP 2'
                        to targetPhysicalPort ::> 'CDT_System Project'::'CDT_System'::'Physical Architecture'::'Structure'::'Physical System'.'Cell Network'.'PP 1' {
                        attribute :>> interfaceName = "Internet"; 
                    }  
                    interface 'f9617c9b-7337-4817-8a66-cd2a71fda0c3' : PhysicalLink 
                        connect sourcePhysicalPort ::> 'CDT_System Project'::'CDT_System'::'Physical Architecture'::'Structure'::'Physical System'.'Cell Network'.'PP 2'
                        to targetPhysicalPort ::> 'CDT_System Project'::'CDT_System'::'Physical Architecture'::'Structure'::'Physical System'.'Smartphone'.'PP 1' {
                        attribute :>> interfaceName = "Cellular"; 
                    }  
                    interface 'af8d9743-7c6e-423b-bc26-388aaca51cd5' : PhysicalLink 
                        connect sourcePhysicalPort ::> 'CDT_System Project'::'CDT_System'::'Physical Architecture'::'Structure'::'Physical System'.'Router'.'To WIFI Network'
                        to targetPhysicalPort ::> 'CDT_System Project'::'CDT_System'::'Physical Architecture'::'Structure'::'Physical System'.'Ipad'.'PP 1' {
                        attribute :>> interfaceName = "WIFI"; 
                    }  
                    interface 'a6a47da1-8ebc-4ec2-b5ee-79fd8db421ea' : PhysicalLink 
                        connect sourcePhysicalPort ::> 'CDT_System Project'::'CDT_System'::'Physical Architecture'::'Structure'::'Physical System'.'Helmet'.'Sensor'.'To IPAD'
                        to targetPhysicalPort ::> 'CDT_System Project'::'CDT_System'::'Physical Architecture'::'Structure'::'Physical System'.'IPAD'.'PP 3' {
                        attribute :>> interfaceName = "Blue tooth"; 
                        attribute 'Physical Properties' : PropertyValueGroup { 
                            attribute 'Maximum Distance (m)' : StringPropertyValue  = '2.0';  
                            attribute 'StringPropertyValue 2' : StringPropertyValue  = 'BLUETOOTH CORE SPECIFICATION Version 5.3' { 
                                attribute :>> summary = "Standard"; 
                            }  
                            ref :>> ownedPropertyValues =  ('CDT_System Project'::'CDT_System'::'Physical Architecture'::'Structure'::'Physical System'.'a6a47da1-8ebc-4ec2-b5ee-79fd8db421ea'.'Physical Properties'.'Maximum Distance (m)',
                            'CDT_System Project'::'CDT_System'::'Physical Architecture'::'Structure'::'Physical System'.'a6a47da1-8ebc-4ec2-b5ee-79fd8db421ea'.'Physical Properties'.'StringPropertyValue 2'); 
                        }  
                         
                        ref :>> ownedPropertyValueGroups =  ('CDT_System Project'::'CDT_System'::'Physical Architecture'::'Structure'::'Physical System'.'a6a47da1-8ebc-4ec2-b5ee-79fd8db421ea'.'Physical Properties'); 
                        ref :>> appliedPropertyValueGroups =  ('CDT_System Project'::'CDT_System'::'Physical Architecture'::'Structure'::'Physical System'.'a6a47da1-8ebc-4ec2-b5ee-79fd8db421ea'.'Physical Properties'); 
                    }  
                    interface 'd4c8c560-66aa-48d7-a1eb-254e80c4ce70' : PhysicalLink 
                        connect sourcePhysicalPort ::> 'CDT_System Project'::'CDT_System'::'Physical Architecture'::'Structure'::'Physical System'.'Router'.'To Local Network CAT 5'
                        to targetPhysicalPort ::> 'CDT_System Project'::'CDT_System'::'Physical Architecture'::'Structure'::'Physical System'.'Athlete Smart Phone'.'PP 1' {
                        attribute :>> interfaceName = "	WIFI"; 
                    }  
                    interface '0a823c44-46ee-42de-8cf3-2e815731a5e8' : PhysicalLink 
                        connect sourcePhysicalPort ::> 'CDT_System Project'::'CDT_System'::'Physical Architecture'::'Structure'::'Physical System'.'Router'.'To Local Network CAT 5'
                        to targetPhysicalPort ::> 'CDT_System Project'::'CDT_System'::'Physical Architecture'::'Structure'::'Physical System'.'ID Programmer'.'PP 1' {
                        attribute :>> interfaceName = "ID to Router"; 
                    }  
                    interface '9c18b552-1693-4388-aa61-aa267158d6bc' : ComponentExchange 
                        connect source ::> 'CDT_System Project'::'CDT_System'::'Physical Architecture'::'Structure'::'Physical System'.'Sensing Device'.'CP 1'
                        to  target ::> 'CDT_System Project'::'CDT_System'::'Physical Architecture'::'Structure'::'Physical System'.'Helium RS Connect'.'From LORAWAN Sensors' { 
                        attribute :>> isOriented = false; 
                        attribute :>> interfaceName = "LORA "; 
                        attribute :>> kind = ComponentExchangeKind::FLOW; 
                        allocation '15fd8f7b-cdd4-4014-9a04-3920758ad584' : ComponentExchangeFunctionalExchangeAllocation
                            allocate functionalExchange ::> 'CDT_System Project'::'CDT_System'::'Physical Architecture'::'Physical Functions'::'Root Physical Function'.'69140741-68f0-453d-858b-b6395ac5cdb0'
                            to componentExchange ::> 'CDT_System Project'::'CDT_System'::'Physical Architecture'::'Structure'::'Physical System'.'9c18b552-1693-4388-aa61-aa267158d6bc'; 
                        allocation 'c3853ccb-b481-4c07-84db-7b10b14f4d63' : ComponentExchangeFunctionalExchangeAllocation
                            allocate functionalExchange ::> 'CDT_System Project'::'CDT_System'::'Physical Architecture'::'Physical Functions'::'Root Physical Function'.'512d646a-097e-4801-9a13-cd5ecc3487dc'
                            to componentExchange ::> 'CDT_System Project'::'CDT_System'::'Physical Architecture'::'Structure'::'Physical System'.'9c18b552-1693-4388-aa61-aa267158d6bc'; 
                        attribute 'Logical Properties' : PropertyValueGroup { 
                            attribute 'LORAWAN Network' : StringPropertyValue  = 'Helium';  
                            ref :>> ownedPropertyValues =  ('CDT_System Project'::'CDT_System'::'Physical Architecture'::'Structure'::'Physical System'.'9c18b552-1693-4388-aa61-aa267158d6bc'.'Logical Properties'.'LORAWAN Network'); 
                        }  
                        ref :>> ownedComponentExchangeFunctionalExchangeAllocations =  ('CDT_System Project'::'CDT_System'::'Physical Architecture'::'Structure'::'Physical System'.'9c18b552-1693-4388-aa61-aa267158d6bc'.'15fd8f7b-cdd4-4014-9a04-3920758ad584',
                        'CDT_System Project'::'CDT_System'::'Physical Architecture'::'Structure'::'Physical System'.'9c18b552-1693-4388-aa61-aa267158d6bc'.'c3853ccb-b481-4c07-84db-7b10b14f4d63'); 
                        ref :>> ownedPropertyValueGroups =  ('CDT_System Project'::'CDT_System'::'Physical Architecture'::'Structure'::'Physical System'.'9c18b552-1693-4388-aa61-aa267158d6bc'.'Logical Properties'); 
                        ref :>> appliedPropertyValueGroups =  ('CDT_System Project'::'CDT_System'::'Physical Architecture'::'Structure'::'Physical System'.'9c18b552-1693-4388-aa61-aa267158d6bc'.'Logical Properties'); 
                    }  
                    interface '6a55dd77-1ac8-4d27-be57-b1caf64c3cf1' : ComponentExchange 
                        connect source ::> 'CDT_System Project'::'CDT_System'::'Physical Architecture'::'Structure'::'Physical System'.'Sensing Device'.'CP 2'
                        to  target ::> 'CDT_System Project'::'CDT_System'::'Physical Architecture'::'Structure'::'Physical System'.'Bluetooth'.'CP 1' { 
                        attribute :>> isOriented = false; 
                        attribute :>> interfaceName = "Bluetoth"; 
                        attribute :>> kind = ComponentExchangeKind::FLOW; 
                        allocation '9c13c520-81fe-4686-a3d1-709fb41fd984' : ComponentExchangeFunctionalExchangeAllocation
                            allocate functionalExchange ::> 'CDT_System Project'::'CDT_System'::'Physical Architecture'::'Physical Functions'::'Root Physical Function'.'Data is Retrieved'.'f3b6024c-0813-4c5f-9fbc-ab871dca9975'
                            to componentExchange ::> 'CDT_System Project'::'CDT_System'::'Physical Architecture'::'Structure'::'Physical System'.'6a55dd77-1ac8-4d27-be57-b1caf64c3cf1'; 
                        allocation '742f3ba8-bac7-42e3-8a7a-d74dead865de' : ComponentExchangeFunctionalExchangeAllocation
                            allocate functionalExchange ::> 'CDT_System Project'::'CDT_System'::'Physical Architecture'::'Physical Functions'::'Root Physical Function'.'Enable Monitoring'.'2c6482ad-1fc7-43d2-850c-7e17848fe27a'
                            to componentExchange ::> 'CDT_System Project'::'CDT_System'::'Physical Architecture'::'Structure'::'Physical System'.'6a55dd77-1ac8-4d27-be57-b1caf64c3cf1'; 
                        ref :>> ownedComponentExchangeFunctionalExchangeAllocations =  ('CDT_System Project'::'CDT_System'::'Physical Architecture'::'Structure'::'Physical System'.'6a55dd77-1ac8-4d27-be57-b1caf64c3cf1'.'9c13c520-81fe-4686-a3d1-709fb41fd984',
                        'CDT_System Project'::'CDT_System'::'Physical Architecture'::'Structure'::'Physical System'.'6a55dd77-1ac8-4d27-be57-b1caf64c3cf1'.'742f3ba8-bac7-42e3-8a7a-d74dead865de'); 
                    }  
                    interface 'aa5f61ae-8092-460c-bf47-dfa3e25e8e65' : ComponentExchange 
                        connect source ::> 'CDT_System Project'::'CDT_System'::'Physical Architecture'::'Structure'::'Physical System'.'Bluetooth'.'CP 2'
                        to  target ::> 'CDT_System Project'::'CDT_System'::'Physical Architecture'::'Structure'::'Physical System'.'CDT App'.'CP 2' { 
                        attribute :>> isOriented = false; 
                        attribute :>> interfaceName = "BT Data"; 
                        attribute :>> kind = ComponentExchangeKind::FLOW; 
                    }  
                    interface '1438c433-9b09-4395-82e0-10a3be0be574' : ComponentExchange 
                        connect source ::> 'CDT_System Project'::'CDT_System'::'Physical Architecture'::'Structure'::'Physical System'.'Helium RS Connect'.'To Cloud Console'
                        to  target ::> 'CDT_System Project'::'CDT_System'::'Physical Architecture'::'Structure'::'Physical System'.'Secure Application'.'CP 1' { 
                        attribute :>> isOriented = false; 
                        attribute :>> interfaceName = "HS to SA"; 
                        attribute :>> kind = ComponentExchangeKind::FLOW; 
                        allocation 'fd14980b-1713-4b1f-b278-fe6cdc38b855' : ComponentExchangeFunctionalExchangeAllocation
                            allocate functionalExchange ::> 'CDT_System Project'::'CDT_System'::'Physical Architecture'::'Physical Functions'::'Root Physical Function'.'47c4e8e5-b091-4e08-a377-9a091f71beac'
                            to componentExchange ::> 'CDT_System Project'::'CDT_System'::'Physical Architecture'::'Structure'::'Physical System'.'1438c433-9b09-4395-82e0-10a3be0be574'; 
                        allocation '1303c9b7-d9f1-4bba-b91f-6e5d023f88ac' : ComponentExchangeFunctionalExchangeAllocation
                            allocate functionalExchange ::> 'CDT_System Project'::'CDT_System'::'Physical Architecture'::'Physical Functions'::'Root Physical Function'.'33c7de34-5819-4162-a02e-b2d39af813fa'
                            to componentExchange ::> 'CDT_System Project'::'CDT_System'::'Physical Architecture'::'Structure'::'Physical System'.'1438c433-9b09-4395-82e0-10a3be0be574'; 
                        ref :>> ownedComponentExchangeFunctionalExchangeAllocations =  ('CDT_System Project'::'CDT_System'::'Physical Architecture'::'Structure'::'Physical System'.'1438c433-9b09-4395-82e0-10a3be0be574'.'fd14980b-1713-4b1f-b278-fe6cdc38b855',
                        'CDT_System Project'::'CDT_System'::'Physical Architecture'::'Structure'::'Physical System'.'1438c433-9b09-4395-82e0-10a3be0be574'.'1303c9b7-d9f1-4bba-b91f-6e5d023f88ac'); 
                    }  
                    interface '9e78b73f-8edd-49d5-8c28-52f4afc8375b' : ComponentExchange 
                        connect source ::> 'CDT_System Project'::'CDT_System'::'Physical Architecture'::'Structure'::'Physical System'.'Secure Application'.'CP 5'
                        to  target ::> 'CDT_System Project'::'CDT_System'::'Physical Architecture'::'Structure'::'Physical System'.'CDT App'.'CP 3' { 
                        attribute :>> isOriented = false; 
                        attribute :>> interfaceName = "SA to Trainer"; 
                        attribute :>> kind = ComponentExchangeKind::FLOW; 
                        allocation '4e4d19ab-478d-440d-bd9b-03ee1b043738' : ComponentExchangeFunctionalExchangeAllocation
                            allocate functionalExchange ::> 'CDT_System Project'::'CDT_System'::'Physical Architecture'::'Physical Functions'::'Root Physical Function'.'Store Profile'.'bbf0f4ef-a3b4-4fef-846c-4126655a355e'
                            to componentExchange ::> 'CDT_System Project'::'CDT_System'::'Physical Architecture'::'Structure'::'Physical System'.'9e78b73f-8edd-49d5-8c28-52f4afc8375b'; 
                        allocation '899797cf-4e79-4401-919f-fcb8265cfd56' : ComponentExchangeFunctionalExchangeAllocation
                            allocate functionalExchange ::> 'CDT_System Project'::'CDT_System'::'Physical Architecture'::'Physical Functions'::'Root Physical Function'.'Device alerts possible Concussion'.'45e34246-c2d7-4145-9057-e7c08a0e81f0'
                            to componentExchange ::> 'CDT_System Project'::'CDT_System'::'Physical Architecture'::'Structure'::'Physical System'.'9e78b73f-8edd-49d5-8c28-52f4afc8375b'; 
                        allocation '51df97dd-8ba9-449f-b9cd-b69e1ef3516e' : ComponentExchangeFunctionalExchangeAllocation
                            allocate functionalExchange ::> 'CDT_System Project'::'CDT_System'::'Physical Architecture'::'Physical Functions'::'Root Physical Function'.'23e5f028-b459-46de-b970-6d260ce6ca65'
                            to componentExchange ::> 'CDT_System Project'::'CDT_System'::'Physical Architecture'::'Structure'::'Physical System'.'9e78b73f-8edd-49d5-8c28-52f4afc8375b'; 
                        allocation '240a481b-7ac0-4c41-85f6-9111bd76d77b' : ComponentExchangeFunctionalExchangeAllocation
                            allocate functionalExchange ::> 'CDT_System Project'::'CDT_System'::'Physical Architecture'::'Physical Functions'::'Root Physical Function'.'Enable Monitoring'.'a3dffb1d-7f69-44be-bf54-3573dc31d2b1'
                            to componentExchange ::> 'CDT_System Project'::'CDT_System'::'Physical Architecture'::'Structure'::'Physical System'.'9e78b73f-8edd-49d5-8c28-52f4afc8375b'; 
                        allocation '5e68a7b1-453d-4639-a59a-2c97592098a2' : ComponentExchangeFunctionalExchangeAllocation
                            allocate functionalExchange ::> 'CDT_System Project'::'CDT_System'::'Physical Architecture'::'Physical Functions'::'Root Physical Function'.'Data stored'.'c2037e08-ff2e-4992-8194-54e202827a7f'
                            to componentExchange ::> 'CDT_System Project'::'CDT_System'::'Physical Architecture'::'Structure'::'Physical System'.'9e78b73f-8edd-49d5-8c28-52f4afc8375b'; 
                        allocation '0a3ec8f8-0e59-4ab6-8e31-c72d1d84a0f2' : ComponentExchangeFunctionalExchangeAllocation
                            allocate functionalExchange ::> 'CDT_System Project'::'CDT_System'::'Physical Architecture'::'Physical Functions'::'Root Physical Function'.'Generates Reports'.'4f5a07ad-1c1c-43f4-8ee0-2ca39f0be65b'
                            to componentExchange ::> 'CDT_System Project'::'CDT_System'::'Physical Architecture'::'Structure'::'Physical System'.'9e78b73f-8edd-49d5-8c28-52f4afc8375b'; 
                        allocation '3634b771-f26c-4f23-944c-d49c1a8db424' : ComponentExchangeFunctionalExchangeAllocation
                            allocate functionalExchange ::> 'CDT_System Project'::'CDT_System'::'Physical Architecture'::'Physical Functions'::'Root Physical Function'.'Create Unique IDs for Athlete'.'147dc2ae-62f1-446c-80ed-32ffb3ecef78'
                            to componentExchange ::> 'CDT_System Project'::'CDT_System'::'Physical Architecture'::'Structure'::'Physical System'.'9e78b73f-8edd-49d5-8c28-52f4afc8375b'; 
                        ref :>> ownedComponentExchangeFunctionalExchangeAllocations =  ('CDT_System Project'::'CDT_System'::'Physical Architecture'::'Structure'::'Physical System'.'9e78b73f-8edd-49d5-8c28-52f4afc8375b'.'4e4d19ab-478d-440d-bd9b-03ee1b043738',
                        'CDT_System Project'::'CDT_System'::'Physical Architecture'::'Structure'::'Physical System'.'9e78b73f-8edd-49d5-8c28-52f4afc8375b'.'899797cf-4e79-4401-919f-fcb8265cfd56',
                        'CDT_System Project'::'CDT_System'::'Physical Architecture'::'Structure'::'Physical System'.'9e78b73f-8edd-49d5-8c28-52f4afc8375b'.'51df97dd-8ba9-449f-b9cd-b69e1ef3516e',
                        'CDT_System Project'::'CDT_System'::'Physical Architecture'::'Structure'::'Physical System'.'9e78b73f-8edd-49d5-8c28-52f4afc8375b'.'240a481b-7ac0-4c41-85f6-9111bd76d77b',
                        'CDT_System Project'::'CDT_System'::'Physical Architecture'::'Structure'::'Physical System'.'9e78b73f-8edd-49d5-8c28-52f4afc8375b'.'5e68a7b1-453d-4639-a59a-2c97592098a2',
                        'CDT_System Project'::'CDT_System'::'Physical Architecture'::'Structure'::'Physical System'.'9e78b73f-8edd-49d5-8c28-52f4afc8375b'.'0a3ec8f8-0e59-4ab6-8e31-c72d1d84a0f2',
                        'CDT_System Project'::'CDT_System'::'Physical Architecture'::'Structure'::'Physical System'.'9e78b73f-8edd-49d5-8c28-52f4afc8375b'.'3634b771-f26c-4f23-944c-d49c1a8db424'); 
                    }  
                    interface '18ee325b-97d3-4738-b0a4-e8a83219ebf7' : ComponentExchange 
                        connect source ::> 'CDT_System Project'::'CDT_System'::'Physical Architecture'::'Structure'::'Physical System'.'ID Device'.'CP 1'
                        to  target ::> 'CDT_System Project'::'CDT_System'::'Physical Architecture'::'Structure'::'Physical System'.'Sensing Device'.'CP 3' { 
                        attribute :>> isOriented = false; 
                        attribute :>> interfaceName = "ID to SD"; 
                        attribute :>> kind = ComponentExchangeKind::FLOW; 
                        allocation '5fc2ca67-cd1d-4c1a-b21d-506915eeaf59' : ComponentExchangeFunctionalExchangeAllocation
                            allocate functionalExchange ::> 'CDT_System Project'::'CDT_System'::'Physical Architecture'::'Physical Functions'::'Root Physical Function'.'7d222aa7-b806-4a69-9cab-674e9f1e0de0'
                            to componentExchange ::> 'CDT_System Project'::'CDT_System'::'Physical Architecture'::'Structure'::'Physical System'.'18ee325b-97d3-4738-b0a4-e8a83219ebf7'; 
                        ref :>> ownedComponentExchangeFunctionalExchangeAllocations =  ('CDT_System Project'::'CDT_System'::'Physical Architecture'::'Structure'::'Physical System'.'18ee325b-97d3-4738-b0a4-e8a83219ebf7'.'5fc2ca67-cd1d-4c1a-b21d-506915eeaf59'); 
                    }  
                    interface '37f49142-66fb-4a90-9786-db252e703cb3' : ComponentExchange 
                        connect source ::> 'CDT_System Project'::'CDT_System'::'Physical Architecture'::'Structure'::'Physical System'.'Helmet'.'CP 2'
                        to  target ::> 'CDT_System Project'::'CDT_System'::'Physical Architecture'::'Structure'::'Physical System'.'Sensing Device'.'CP 4' { 
                        attribute :>> isOriented = false; 
                        attribute :>> interfaceName = "Helmut to Sensor"; 
                        attribute :>> kind = ComponentExchangeKind::FLOW; 
                        allocation '707788b6-0743-47e2-b1cd-43a1273d59b6' : ComponentExchangeFunctionalExchangeAllocation
                            allocate functionalExchange ::> 'CDT_System Project'::'CDT_System'::'Physical Architecture'::'Physical Functions'::'Root Physical Function'.'9d36dfac-6872-4444-b1bd-2a76b69f97ad'
                            to componentExchange ::> 'CDT_System Project'::'CDT_System'::'Physical Architecture'::'Structure'::'Physical System'.'37f49142-66fb-4a90-9786-db252e703cb3'; 
                        allocation 'e03f2d09-8e0b-4a5d-857d-a99c8717843c' : ComponentExchangeFunctionalExchangeAllocation
                            allocate functionalExchange ::> 'CDT_System Project'::'CDT_System'::'Physical Architecture'::'Physical Functions'::'Root Physical Function'.'7b17df23-af62-44ed-acba-7747c33550e5'
                            to componentExchange ::> 'CDT_System Project'::'CDT_System'::'Physical Architecture'::'Structure'::'Physical System'.'37f49142-66fb-4a90-9786-db252e703cb3'; 
                        ref :>> ownedComponentExchangeFunctionalExchangeAllocations =  ('CDT_System Project'::'CDT_System'::'Physical Architecture'::'Structure'::'Physical System'.'37f49142-66fb-4a90-9786-db252e703cb3'.'707788b6-0743-47e2-b1cd-43a1273d59b6',
                        'CDT_System Project'::'CDT_System'::'Physical Architecture'::'Structure'::'Physical System'.'37f49142-66fb-4a90-9786-db252e703cb3'.'e03f2d09-8e0b-4a5d-857d-a99c8717843c'); 
                    }  
                    interface '5e2659f5-7477-49a7-acf9-2c846cde6a21' : ComponentExchange 
                        connect source ::> 'CDT_System Project'::'CDT_System'::'Physical Architecture'::'Structure'::'Physical System'.'Secure Application'.'CP 6'
                        to  target ::> 'CDT_System Project'::'CDT_System'::'Physical Architecture'::'Structure'::'Physical System'.'ID Programmer'.'CP 1' { 
                        attribute :>> isOriented = false; 
                        attribute :>> interfaceName = "SA to P"; 
                        attribute :>> kind = ComponentExchangeKind::FLOW; 
                        allocation '8eaa84f5-e356-4b6e-877e-e58d6a3c7313' : ComponentExchangeFunctionalExchangeAllocation
                            allocate functionalExchange ::> 'CDT_System Project'::'CDT_System'::'Physical Architecture'::'Physical Functions'::'Root Physical Function'.'Create Unique IDs for Athlete'.'c720e95c-2fd1-461d-989f-de4a3723ad3d'
                            to componentExchange ::> 'CDT_System Project'::'CDT_System'::'Physical Architecture'::'Structure'::'Physical System'.'5e2659f5-7477-49a7-acf9-2c846cde6a21'; 
                        ref :>> ownedComponentExchangeFunctionalExchangeAllocations =  ('CDT_System Project'::'CDT_System'::'Physical Architecture'::'Structure'::'Physical System'.'5e2659f5-7477-49a7-acf9-2c846cde6a21'.'8eaa84f5-e356-4b6e-877e-e58d6a3c7313'); 
                    }  
                    interface 'cb5717f6-7ad6-4c0a-ac25-cb0bccf022bc' : ComponentExchange 
                        connect source ::> 'CDT_System Project'::'CDT_System'::'Physical Architecture'::'Structure'::'Physical System'.'ID Programmer'.'CP 2'
                        to  target ::> 'CDT_System Project'::'CDT_System'::'Physical Architecture'::'Structure'::'Physical System'.'ID Device'.'CP 2' { 
                        attribute :>> isOriented = false; 
                        attribute :>> interfaceName = "P to ID"; 
                        attribute :>> kind = ComponentExchangeKind::FLOW; 
                        allocation '850bcb29-b73f-4ff0-bb62-6182ae9c8ad7' : ComponentExchangeFunctionalExchangeAllocation
                            allocate functionalExchange ::> 'CDT_System Project'::'CDT_System'::'Physical Architecture'::'Physical Functions'::'Root Physical Function'.'Create Unique IDs for Athlete'.'Create and Program ID'.'4b9d7e5b-2d87-451c-8c78-ba39e562a889'
                            to componentExchange ::> 'CDT_System Project'::'CDT_System'::'Physical Architecture'::'Structure'::'Physical System'.'cb5717f6-7ad6-4c0a-ac25-cb0bccf022bc'; 
                        ref :>> ownedComponentExchangeFunctionalExchangeAllocations =  ('CDT_System Project'::'CDT_System'::'Physical Architecture'::'Structure'::'Physical System'.'cb5717f6-7ad6-4c0a-ac25-cb0bccf022bc'.'850bcb29-b73f-4ff0-bb62-6182ae9c8ad7'); 
                    }  
                    part 'Secure Application' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation 'beb1f7a1-26c8-4a24-8971-9c0e521edcff' : ComponentFunctionalAllocation
                            allocate function ::> 'CDT_System Project'::'CDT_System'::'Physical Architecture'::'Physical Functions'::'Root Physical Function'.'Device alerts possible Concussion'.'Record the Concussion'
                            to component ::> 'CDT_System Project'::'CDT_System'::'Physical Architecture'::'Structure'::'Physical System'.'Secure Application';
                        perform 'CDT_System Project'::'CDT_System'::'Physical Architecture'::'Physical Functions'::'Root Physical Function'.'Device alerts possible Concussion'.'Record the Concussion' ; 
                        allocation '61f052eb-24e8-4c7f-801b-6af1400ddc27' : ComponentFunctionalAllocation
                            allocate function ::> 'CDT_System Project'::'CDT_System'::'Physical Architecture'::'Physical Functions'::'Root Physical Function'.'Data stored'.'Data Stored'
                            to component ::> 'CDT_System Project'::'CDT_System'::'Physical Architecture'::'Structure'::'Physical System'.'Secure Application';
                        perform 'CDT_System Project'::'CDT_System'::'Physical Architecture'::'Physical Functions'::'Root Physical Function'.'Data stored'.'Data Stored' ; 
                        allocation '495c7dca-5c40-4815-a410-c14ac4343e8c' : ComponentFunctionalAllocation
                            allocate function ::> 'CDT_System Project'::'CDT_System'::'Physical Architecture'::'Physical Functions'::'Root Physical Function'.'Generates Reports'.'Generate Reports'
                            to component ::> 'CDT_System Project'::'CDT_System'::'Physical Architecture'::'Structure'::'Physical System'.'Secure Application';
                        perform 'CDT_System Project'::'CDT_System'::'Physical Architecture'::'Physical Functions'::'Root Physical Function'.'Generates Reports'.'Generate Reports' ; 
                        allocation 'a750303f-b9f8-47c1-875d-1f2ca903d7af' : ComponentFunctionalAllocation
                            allocate function ::> 'CDT_System Project'::'CDT_System'::'Physical Architecture'::'Physical Functions'::'Root Physical Function'.'Enable Monitoring'.'Enable Recored'
                            to component ::> 'CDT_System Project'::'CDT_System'::'Physical Architecture'::'Structure'::'Physical System'.'Secure Application';
                        perform 'CDT_System Project'::'CDT_System'::'Physical Architecture'::'Physical Functions'::'Root Physical Function'.'Enable Monitoring'.'Enable Recored' ; 
                        allocation '95359171-7918-4c33-86b0-fa40e96961ab' : ComponentFunctionalAllocation
                            allocate function ::> 'CDT_System Project'::'CDT_System'::'Physical Architecture'::'Physical Functions'::'Root Physical Function'.'Store Profile'.'Store Profile'
                            to component ::> 'CDT_System Project'::'CDT_System'::'Physical Architecture'::'Structure'::'Physical System'.'Secure Application';
                        perform 'CDT_System Project'::'CDT_System'::'Physical Architecture'::'Physical Functions'::'Root Physical Function'.'Store Profile'.'Store Profile' ; 
                        allocation '4c02c393-28c2-46a9-ac71-b2c74f57baca' : ComponentFunctionalAllocation
                            allocate function ::> 'CDT_System Project'::'CDT_System'::'Physical Architecture'::'Physical Functions'::'Root Physical Function'.'Create Unique IDs for Athlete'.'Create ID'
                            to component ::> 'CDT_System Project'::'CDT_System'::'Physical Architecture'::'Structure'::'Physical System'.'Secure Application';
                        perform 'CDT_System Project'::'CDT_System'::'Physical Architecture'::'Physical Functions'::'Root Physical Function'.'Create Unique IDs for Athlete'.'Create ID' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::INOUT; 
                            attribute :>> isUnique = false; 
                            attribute :>> isReadOnly = false; 
                            attribute :>> isMinInclusive = false; 
                            attribute :>> isStatic = false; 
                            attribute :>> isOrdered = false; 
                            attribute :>> isAbstract = false; 
                            ref allocation '46429c74-8895-46cd-af81-59ed26c16715' : PortAllocation
                                allocate allocatedPort ::> 'CDT_System Project'::'CDT_System'::'Physical Architecture'::'Physical Functions'::'Root Physical Function'.'Device alerts possible Concussion'.'Record the Concussion'.'FIP 1'
                                to allocatingPort ::> 'CDT_System Project'::'CDT_System'::'Physical Architecture'::'Structure'::'Physical System'.'Secure Application'.'CP 1'; 
                            ref allocation '1142701b-245a-4f3b-a091-375c5f0f28c6' : PortAllocation
                                allocate allocatedPort ::> 'CDT_System Project'::'CDT_System'::'Physical Architecture'::'Physical Functions'::'Root Physical Function'.'Enable Monitoring'.'Enable Recored'.'FIP 1'
                                to allocatingPort ::> 'CDT_System Project'::'CDT_System'::'Physical Architecture'::'Structure'::'Physical System'.'Secure Application'.'CP 1'; 
                            ref :>> ownedPortAllocations =  ('CDT_System Project'::'CDT_System'::'Physical Architecture'::'Structure'::'Physical System'.'Secure Application'.'CP 1'.'46429c74-8895-46cd-af81-59ed26c16715',
                            'CDT_System Project'::'CDT_System'::'Physical Architecture'::'Structure'::'Physical System'.'Secure Application'.'CP 1'.'1142701b-245a-4f3b-a091-375c5f0f28c6'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '845abf02-5e30-4462-998d-d9f17512a70e' : PortAllocation
                                allocate allocatedPort ::> 'CDT_System Project'::'CDT_System'::'Physical Architecture'::'Physical Functions'::'Root Physical Function'.'Generates Reports'.'Generate Reports'.'outParen Report'
                                to allocatingPort ::> 'CDT_System Project'::'CDT_System'::'Physical Architecture'::'Structure'::'Physical System'.'Secure Application'.'CP 2'; 
                            ref :>> ownedPortAllocations =  ('CDT_System Project'::'CDT_System'::'Physical Architecture'::'Structure'::'Physical System'.'Secure Application'.'CP 2'.'845abf02-5e30-4462-998d-d9f17512a70e'); 
                        }  
                        port 'CP 3' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '5988ef6b-0bb2-4e65-b336-444844bb21c6' : PortAllocation
                                allocate allocatedPort ::> 'CDT_System Project'::'CDT_System'::'Physical Architecture'::'Physical Functions'::'Root Physical Function'.'Generates Reports'.'Generate Reports'.'outInstition Report'
                                to allocatingPort ::> 'CDT_System Project'::'CDT_System'::'Physical Architecture'::'Structure'::'Physical System'.'Secure Application'.'CP 3'; 
                            ref :>> ownedPortAllocations =  ('CDT_System Project'::'CDT_System'::'Physical Architecture'::'Structure'::'Physical System'.'Secure Application'.'CP 3'.'5988ef6b-0bb2-4e65-b336-444844bb21c6'); 
                        }  
                        port 'CP 4' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '17e41f79-13ad-45ee-be9e-5c54afeb4325' : PortAllocation
                                allocate allocatedPort ::> 'CDT_System Project'::'CDT_System'::'Physical Architecture'::'Physical Functions'::'Root Physical Function'.'Generates Reports'.'Generate Reports'.'outAthlete Report'
                                to allocatingPort ::> 'CDT_System Project'::'CDT_System'::'Physical Architecture'::'Structure'::'Physical System'.'Secure Application'.'CP 4'; 
                            ref :>> ownedPortAllocations =  ('CDT_System Project'::'CDT_System'::'Physical Architecture'::'Structure'::'Physical System'.'Secure Application'.'CP 4'.'17e41f79-13ad-45ee-be9e-5c54afeb4325'); 
                        }  
                        port 'CP 5' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'cbb37783-3964-450b-ab94-ae3704743978' : PortAllocation
                                allocate allocatedPort ::> 'CDT_System Project'::'CDT_System'::'Physical Architecture'::'Physical Functions'::'Root Physical Function'.'Store Profile'.'Store Profile'.'FIP 1'
                                to allocatingPort ::> 'CDT_System Project'::'CDT_System'::'Physical Architecture'::'Structure'::'Physical System'.'Secure Application'.'CP 5'; 
                            ref allocation '351db9e5-f574-4cc5-8dca-113b43f2fe76' : PortAllocation
                                allocate allocatedPort ::> 'CDT_System Project'::'CDT_System'::'Physical Architecture'::'Physical Functions'::'Root Physical Function'.'Device alerts possible Concussion'.'Record the Concussion'.'FOP 2'
                                to allocatingPort ::> 'CDT_System Project'::'CDT_System'::'Physical Architecture'::'Structure'::'Physical System'.'Secure Application'.'CP 5'; 
                            ref allocation '096c224f-1790-4e07-a3fa-3164f62ab08c' : PortAllocation
                                allocate allocatedPort ::> 'CDT_System Project'::'CDT_System'::'Physical Architecture'::'Physical Functions'::'Root Physical Function'.'Data stored'.'Data Stored'.'inRecorded Data'
                                to allocatingPort ::> 'CDT_System Project'::'CDT_System'::'Physical Architecture'::'Structure'::'Physical System'.'Secure Application'.'CP 5'; 
                            ref allocation '194f3c7d-1012-4d19-8462-360d39f67261' : PortAllocation
                                allocate allocatedPort ::> 'CDT_System Project'::'CDT_System'::'Physical Architecture'::'Physical Functions'::'Root Physical Function'.'Enable Monitoring'.'Enable Recored'.'FOP 1'
                                to allocatingPort ::> 'CDT_System Project'::'CDT_System'::'Physical Architecture'::'Structure'::'Physical System'.'Secure Application'.'CP 5'; 
                            ref allocation '4e50a82e-f2a1-4476-9a55-5ac5a1b41312' : PortAllocation
                                allocate allocatedPort ::> 'CDT_System Project'::'CDT_System'::'Physical Architecture'::'Physical Functions'::'Root Physical Function'.'Data stored'.'Data Stored'.'FOP 1'
                                to allocatingPort ::> 'CDT_System Project'::'CDT_System'::'Physical Architecture'::'Structure'::'Physical System'.'Secure Application'.'CP 5'; 
                            ref allocation '6d744d6c-1522-4d0f-8de9-b78016e8ae06' : PortAllocation
                                allocate allocatedPort ::> 'CDT_System Project'::'CDT_System'::'Physical Architecture'::'Physical Functions'::'Root Physical Function'.'Generates Reports'.'Generate Reports'.'FIP 1'
                                to allocatingPort ::> 'CDT_System Project'::'CDT_System'::'Physical Architecture'::'Structure'::'Physical System'.'Secure Application'.'CP 5'; 
                            ref allocation 'e40c7838-d86f-4a63-b30e-d44fe5dcf8c8' : PortAllocation
                                allocate allocatedPort ::> 'CDT_System Project'::'CDT_System'::'Physical Architecture'::'Physical Functions'::'Root Physical Function'.'Create Unique IDs for Athlete'.'Create ID'.'FIP 1'
                                to allocatingPort ::> 'CDT_System Project'::'CDT_System'::'Physical Architecture'::'Structure'::'Physical System'.'Secure Application'.'CP 5'; 
                            ref :>> ownedPortAllocations =  ('CDT_System Project'::'CDT_System'::'Physical Architecture'::'Structure'::'Physical System'.'Secure Application'.'CP 5'.'cbb37783-3964-450b-ab94-ae3704743978',
                            'CDT_System Project'::'CDT_System'::'Physical Architecture'::'Structure'::'Physical System'.'Secure Application'.'CP 5'.'351db9e5-f574-4cc5-8dca-113b43f2fe76',
                            'CDT_System Project'::'CDT_System'::'Physical Architecture'::'Structure'::'Physical System'.'Secure Application'.'CP 5'.'096c224f-1790-4e07-a3fa-3164f62ab08c',
                            'CDT_System Project'::'CDT_System'::'Physical Architecture'::'Structure'::'Physical System'.'Secure Application'.'CP 5'.'194f3c7d-1012-4d19-8462-360d39f67261',
                            'CDT_System Project'::'CDT_System'::'Physical Architecture'::'Structure'::'Physical System'.'Secure Application'.'CP 5'.'4e50a82e-f2a1-4476-9a55-5ac5a1b41312',
                            'CDT_System Project'::'CDT_System'::'Physical Architecture'::'Structure'::'Physical System'.'Secure Application'.'CP 5'.'6d744d6c-1522-4d0f-8de9-b78016e8ae06',
                            'CDT_System Project'::'CDT_System'::'Physical Architecture'::'Structure'::'Physical System'.'Secure Application'.'CP 5'.'e40c7838-d86f-4a63-b30e-d44fe5dcf8c8'); 
                        }  
                        port 'CP 6' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '7c382fe8-1bd0-42dc-be2e-234a3401b5bb' : PortAllocation
                                allocate allocatedPort ::> 'CDT_System Project'::'CDT_System'::'Physical Architecture'::'Physical Functions'::'Root Physical Function'.'Create Unique IDs for Athlete'.'Create ID'.'FOP 1'
                                to allocatingPort ::> 'CDT_System Project'::'CDT_System'::'Physical Architecture'::'Structure'::'Physical System'.'Secure Application'.'CP 6'; 
                            ref :>> ownedPortAllocations =  ('CDT_System Project'::'CDT_System'::'Physical Architecture'::'Structure'::'Physical System'.'Secure Application'.'CP 6'.'7c382fe8-1bd0-42dc-be2e-234a3401b5bb'); 
                        }  
                        ref :>> ownedFunctionalAllocation =  ('CDT_System Project'::'CDT_System'::'Physical Architecture'::'Structure'::'Physical System'.'Secure Application'.'beb1f7a1-26c8-4a24-8971-9c0e521edcff',
                        'CDT_System Project'::'CDT_System'::'Physical Architecture'::'Structure'::'Physical System'.'Secure Application'.'61f052eb-24e8-4c7f-801b-6af1400ddc27',
                        'CDT_System Project'::'CDT_System'::'Physical Architecture'::'Structure'::'Physical System'.'Secure Application'.'495c7dca-5c40-4815-a410-c14ac4343e8c',
                        'CDT_System Project'::'CDT_System'::'Physical Architecture'::'Structure'::'Physical System'.'Secure Application'.'a750303f-b9f8-47c1-875d-1f2ca903d7af',
                        'CDT_System Project'::'CDT_System'::'Physical Architecture'::'Structure'::'Physical System'.'Secure Application'.'95359171-7918-4c33-86b0-fa40e96961ab',
                        'CDT_System Project'::'CDT_System'::'Physical Architecture'::'Structure'::'Physical System'.'Secure Application'.'4c02c393-28c2-46a9-ac71-b2c74f57baca'); 
                         
                         
                    }  
                    part 'ID Device' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation 'b6c52b85-8dff-4802-9a38-91a26d5d8693' : ComponentFunctionalAllocation
                            allocate function ::> 'CDT_System Project'::'CDT_System'::'Physical Architecture'::'Physical Functions'::'Root Physical Function'.'Provide ID Information'
                            to component ::> 'CDT_System Project'::'CDT_System'::'Physical Architecture'::'Structure'::'Physical System'.'ID Device';
                        perform 'CDT_System Project'::'CDT_System'::'Physical Architecture'::'Physical Functions'::'Root Physical Function'.'Provide ID Information' ; 
                        allocation '1b7aacf5-4370-4a36-91a4-91f3541176f7' : ComponentFunctionalAllocation
                            allocate function ::> 'CDT_System Project'::'CDT_System'::'Physical Architecture'::'Physical Functions'::'Root Physical Function'.'Create Unique IDs for Athlete'.'Create and Program ID'.'Store Encrypted ID'
                            to component ::> 'CDT_System Project'::'CDT_System'::'Physical Architecture'::'Structure'::'Physical System'.'ID Device';
                        perform 'CDT_System Project'::'CDT_System'::'Physical Architecture'::'Physical Functions'::'Root Physical Function'.'Create Unique IDs for Athlete'.'Create and Program ID'.'Store Encrypted ID' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '780dab43-7e77-49c6-b2c9-2d58b472c118' : PortAllocation
                                allocate allocatedPort ::> 'CDT_System Project'::'CDT_System'::'Physical Architecture'::'Physical Functions'::'Root Physical Function'.'Provide ID Information'.'outDevice ID '
                                to allocatingPort ::> 'CDT_System Project'::'CDT_System'::'Physical Architecture'::'Structure'::'Physical System'.'ID Device'.'CP 1'; 
                            ref :>> ownedPortAllocations =  ('CDT_System Project'::'CDT_System'::'Physical Architecture'::'Structure'::'Physical System'.'ID Device'.'CP 1'.'780dab43-7e77-49c6-b2c9-2d58b472c118'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation 'efe122a1-fff7-4ad1-94d3-70711e36f74c' : PortAllocation
                                allocate allocatedPort ::> 'CDT_System Project'::'CDT_System'::'Physical Architecture'::'Physical Functions'::'Root Physical Function'.'Create Unique IDs for Athlete'.'Create and Program ID'.'Store Encrypted ID'.'FIP 1'
                                to allocatingPort ::> 'CDT_System Project'::'CDT_System'::'Physical Architecture'::'Structure'::'Physical System'.'ID Device'.'CP 2'; 
                            ref :>> ownedPortAllocations =  ('CDT_System Project'::'CDT_System'::'Physical Architecture'::'Structure'::'Physical System'.'ID Device'.'CP 2'.'efe122a1-fff7-4ad1-94d3-70711e36f74c'); 
                        }  
                        ref :>> ownedFunctionalAllocation =  ('CDT_System Project'::'CDT_System'::'Physical Architecture'::'Structure'::'Physical System'.'ID Device'.'b6c52b85-8dff-4802-9a38-91a26d5d8693',
                        'CDT_System Project'::'CDT_System'::'Physical Architecture'::'Structure'::'Physical System'.'ID Device'.'1b7aacf5-4370-4a36-91a4-91f3541176f7'); 
                         
                         
                    }  
                    part 'Helmet' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation '63f93da6-c2fa-4df3-b563-e52abd871064' : ComponentFunctionalAllocation
                            allocate function ::> 'CDT_System Project'::'CDT_System'::'Physical Architecture'::'Physical Functions'::'Root Physical Function'.'Provide access to sensing device mounting'
                            to component ::> 'CDT_System Project'::'CDT_System'::'Physical Architecture'::'Structure'::'Physical System'.'Helmet';
                        perform 'CDT_System Project'::'CDT_System'::'Physical Architecture'::'Physical Functions'::'Root Physical Function'.'Provide access to sensing device mounting' ; 
                        allocation '2d6cdfd0-c6c9-4c32-8b7b-7729b14f50c1' : ComponentFunctionalAllocation
                            allocate function ::> 'CDT_System Project'::'CDT_System'::'Physical Architecture'::'Physical Functions'::'Root Physical Function'.'Receive Athlete '
                            to component ::> 'CDT_System Project'::'CDT_System'::'Physical Architecture'::'Structure'::'Physical System'.'Helmet';
                        perform 'CDT_System Project'::'CDT_System'::'Physical Architecture'::'Physical Functions'::'Root Physical Function'.'Receive Athlete ' ; 
                        allocation 'd3a7affe-e736-43f7-8785-32ab42e62833' : ComponentFunctionalAllocation
                            allocate function ::> 'CDT_System Project'::'CDT_System'::'Physical Architecture'::'Physical Functions'::'Root Physical Function'.'Helmet Receives a Hit'
                            to component ::> 'CDT_System Project'::'CDT_System'::'Physical Architecture'::'Structure'::'Physical System'.'Helmet';
                        perform 'CDT_System Project'::'CDT_System'::'Physical Architecture'::'Physical Functions'::'Root Physical Function'.'Helmet Receives a Hit' ; 
                        allocation '6ea31eac-de74-4967-9834-652a3963abfd' : ComponentFunctionalAllocation
                            allocate function ::> 'CDT_System Project'::'CDT_System'::'Physical Architecture'::'Physical Functions'::'Root Physical Function'.'Exit Athlete'
                            to component ::> 'CDT_System Project'::'CDT_System'::'Physical Architecture'::'Structure'::'Physical System'.'Helmet';
                        perform 'CDT_System Project'::'CDT_System'::'Physical Architecture'::'Physical Functions'::'Root Physical Function'.'Exit Athlete' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation 'ac3d98f6-be73-4c58-abe4-300e3c1852e0' : PortAllocation
                                allocate allocatedPort ::> 'CDT_System Project'::'CDT_System'::'Physical Architecture'::'Physical Functions'::'Root Physical Function'.'Receive Athlete '.'inHead '
                                to allocatingPort ::> 'CDT_System Project'::'CDT_System'::'Physical Architecture'::'Structure'::'Physical System'.'Helmet'.'CP 1'; 
                            ref allocation 'c06040b2-a6dc-41cf-bea6-4a113a44b080' : PortAllocation
                                allocate allocatedPort ::> 'CDT_System Project'::'CDT_System'::'Physical Architecture'::'Physical Functions'::'Root Physical Function'.'Exit Athlete'.'FIP 1'
                                to allocatingPort ::> 'CDT_System Project'::'CDT_System'::'Physical Architecture'::'Structure'::'Physical System'.'Helmet'.'CP 1'; 
                            ref :>> ownedPortAllocations =  ('CDT_System Project'::'CDT_System'::'Physical Architecture'::'Structure'::'Physical System'.'Helmet'.'CP 1'.'ac3d98f6-be73-4c58-abe4-300e3c1852e0',
                            'CDT_System Project'::'CDT_System'::'Physical Architecture'::'Structure'::'Physical System'.'Helmet'.'CP 1'.'c06040b2-a6dc-41cf-bea6-4a113a44b080'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '41d8a5ce-ea7f-4ad1-a7aa-7e7aa5c89498' : PortAllocation
                                allocate allocatedPort ::> 'CDT_System Project'::'CDT_System'::'Physical Architecture'::'Physical Functions'::'Root Physical Function'.'Receive Athlete '.'outHelmut Motion'
                                to allocatingPort ::> 'CDT_System Project'::'CDT_System'::'Physical Architecture'::'Structure'::'Physical System'.'Helmet'.'CP 2'; 
                            ref allocation '8c7a695a-563a-4e52-9204-90d71ad19408' : PortAllocation
                                allocate allocatedPort ::> 'CDT_System Project'::'CDT_System'::'Physical Architecture'::'Physical Functions'::'Root Physical Function'.'Helmet Receives a Hit'.'outHit'
                                to allocatingPort ::> 'CDT_System Project'::'CDT_System'::'Physical Architecture'::'Structure'::'Physical System'.'Helmet'.'CP 2'; 
                            ref :>> ownedPortAllocations =  ('CDT_System Project'::'CDT_System'::'Physical Architecture'::'Structure'::'Physical System'.'Helmet'.'CP 2'.'41d8a5ce-ea7f-4ad1-a7aa-7e7aa5c89498',
                            'CDT_System Project'::'CDT_System'::'Physical Architecture'::'Structure'::'Physical System'.'Helmet'.'CP 2'.'8c7a695a-563a-4e52-9204-90d71ad19408'); 
                            ref :>> requiredInterfaces =  ('CDT_System Project'::'CDT_System'::'Physical Architecture'::'Interfaces'::'Helmut to Sensor'); 
                        }  
                        port 'CP 3' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                        }  
                        ref :>> ownedFunctionalAllocation =  ('CDT_System Project'::'CDT_System'::'Physical Architecture'::'Structure'::'Physical System'.'Helmet'.'63f93da6-c2fa-4df3-b563-e52abd871064',
                        'CDT_System Project'::'CDT_System'::'Physical Architecture'::'Structure'::'Physical System'.'Helmet'.'2d6cdfd0-c6c9-4c32-8b7b-7729b14f50c1',
                        'CDT_System Project'::'CDT_System'::'Physical Architecture'::'Structure'::'Physical System'.'Helmet'.'d3a7affe-e736-43f7-8785-32ab42e62833',
                        'CDT_System Project'::'CDT_System'::'Physical Architecture'::'Structure'::'Physical System'.'Helmet'.'6ea31eac-de74-4967-9834-652a3963abfd'); 
                         
                         
                    }  
                    part 'Sensing Device' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation '67370383-11b9-4b17-9f13-6acdc0763d02' : ComponentFunctionalAllocation
                            allocate function ::> 'CDT_System Project'::'CDT_System'::'Physical Architecture'::'Physical Functions'::'Root Physical Function'.'Provide access to helmut mounting'
                            to component ::> 'CDT_System Project'::'CDT_System'::'Physical Architecture'::'Structure'::'Physical System'.'Sensing Device';
                        perform 'CDT_System Project'::'CDT_System'::'Physical Architecture'::'Physical Functions'::'Root Physical Function'.'Provide access to helmut mounting' ; 
                        allocation 'd96f7987-5628-46c7-a029-39a3d86f947c' : ComponentFunctionalAllocation
                            allocate function ::> 'CDT_System Project'::'CDT_System'::'Physical Architecture'::'Physical Functions'::'Root Physical Function'.'Enable Secure Collection'
                            to component ::> 'CDT_System Project'::'CDT_System'::'Physical Architecture'::'Structure'::'Physical System'.'Sensing Device';
                        perform 'CDT_System Project'::'CDT_System'::'Physical Architecture'::'Physical Functions'::'Root Physical Function'.'Enable Secure Collection' ; 
                        allocation 'f2765fc0-a25c-4d0a-b4bf-a71d664c4e31' : ComponentFunctionalAllocation
                            allocate function ::> 'CDT_System Project'::'CDT_System'::'Physical Architecture'::'Physical Functions'::'Root Physical Function'.'Recieve ID'
                            to component ::> 'CDT_System Project'::'CDT_System'::'Physical Architecture'::'Structure'::'Physical System'.'Sensing Device';
                        perform 'CDT_System Project'::'CDT_System'::'Physical Architecture'::'Physical Functions'::'Root Physical Function'.'Recieve ID' ; 
                        allocation '0e75425a-cf64-4176-864c-920ce8c80b18' : ComponentFunctionalAllocation
                            allocate function ::> 'CDT_System Project'::'CDT_System'::'Physical Architecture'::'Physical Functions'::'Root Physical Function'.'Device Detects Activity'
                            to component ::> 'CDT_System Project'::'CDT_System'::'Physical Architecture'::'Structure'::'Physical System'.'Sensing Device';
                        perform 'CDT_System Project'::'CDT_System'::'Physical Architecture'::'Physical Functions'::'Root Physical Function'.'Device Detects Activity' ; 
                        allocation '08c9cb16-f9e2-485a-9828-6f2505829275' : ComponentFunctionalAllocation
                            allocate function ::> 'CDT_System Project'::'CDT_System'::'Physical Architecture'::'Physical Functions'::'Root Physical Function'.'Device alerts possible Concussion'.'Send message'
                            to component ::> 'CDT_System Project'::'CDT_System'::'Physical Architecture'::'Structure'::'Physical System'.'Sensing Device';
                        perform 'CDT_System Project'::'CDT_System'::'Physical Architecture'::'Physical Functions'::'Root Physical Function'.'Device alerts possible Concussion'.'Send message' ; 
                        allocation '7850ee0b-ef28-4650-a16f-3a06ffa20153' : ComponentFunctionalAllocation
                            allocate function ::> 'CDT_System Project'::'CDT_System'::'Physical Architecture'::'Physical Functions'::'Root Physical Function'.'Data is Retrieved'.'Provide Hit Data'
                            to component ::> 'CDT_System Project'::'CDT_System'::'Physical Architecture'::'Structure'::'Physical System'.'Sensing Device';
                        perform 'CDT_System Project'::'CDT_System'::'Physical Architecture'::'Physical Functions'::'Root Physical Function'.'Data is Retrieved'.'Provide Hit Data' ; 
                        allocation 'ddce45d7-13c0-4f5c-a1d1-0926397cfb48' : ComponentFunctionalAllocation
                            allocate function ::> 'CDT_System Project'::'CDT_System'::'Physical Architecture'::'Physical Functions'::'Root Physical Function'.'Enable Monitoring'.'Enable Monitoring'
                            to component ::> 'CDT_System Project'::'CDT_System'::'Physical Architecture'::'Structure'::'Physical System'.'Sensing Device';
                        perform 'CDT_System Project'::'CDT_System'::'Physical Architecture'::'Physical Functions'::'Root Physical Function'.'Enable Monitoring'.'Enable Monitoring' ; 
                        allocation 'd8a7671c-7cf9-4c4b-8e67-eaa7b210f95a' : ComponentFunctionalAllocation
                            allocate function ::> 'CDT_System Project'::'CDT_System'::'Physical Architecture'::'Physical Functions'::'Root Physical Function'.'Enable Monitoring'.'Look for bluetooth connect'
                            to component ::> 'CDT_System Project'::'CDT_System'::'Physical Architecture'::'Structure'::'Physical System'.'Sensing Device';
                        perform 'CDT_System Project'::'CDT_System'::'Physical Architecture'::'Physical Functions'::'Root Physical Function'.'Enable Monitoring'.'Look for bluetooth connect' ; 
                        allocation '33f76bea-4ddb-49dc-8c4d-189b50d1969d' : ComponentFunctionalAllocation
                            allocate function ::> 'CDT_System Project'::'CDT_System'::'Physical Architecture'::'Physical Functions'::'Root Physical Function'.'Disable Monitoring'
                            to component ::> 'CDT_System Project'::'CDT_System'::'Physical Architecture'::'Structure'::'Physical System'.'Sensing Device';
                        perform 'CDT_System Project'::'CDT_System'::'Physical Architecture'::'Physical Functions'::'Root Physical Function'.'Disable Monitoring' ; 
                        allocation 'e1da35fc-a853-4e3f-8420-f2ab1414b968' : ComponentFunctionalAllocation
                            allocate function ::> 'CDT_System Project'::'CDT_System'::'Physical Architecture'::'Physical Functions'::'Root Physical Function'.'Disable Secure Collection'
                            to component ::> 'CDT_System Project'::'CDT_System'::'Physical Architecture'::'Structure'::'Physical System'.'Sensing Device';
                        perform 'CDT_System Project'::'CDT_System'::'Physical Architecture'::'Physical Functions'::'Root Physical Function'.'Disable Secure Collection' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '163dc662-6de6-4e4a-93be-32703a8a6bce' : PortAllocation
                                allocate allocatedPort ::> 'CDT_System Project'::'CDT_System'::'Physical Architecture'::'Physical Functions'::'Root Physical Function'.'Device alerts possible Concussion'.'Send message'.'FOP 1'
                                to allocatingPort ::> 'CDT_System Project'::'CDT_System'::'Physical Architecture'::'Structure'::'Physical System'.'Sensing Device'.'CP 1'; 
                            ref allocation 'ef878e19-1acd-4869-9306-8a211358d7e8' : PortAllocation
                                allocate allocatedPort ::> 'CDT_System Project'::'CDT_System'::'Physical Architecture'::'Physical Functions'::'Root Physical Function'.'Enable Monitoring'.'Enable Monitoring'.'FOP 1'
                                to allocatingPort ::> 'CDT_System Project'::'CDT_System'::'Physical Architecture'::'Structure'::'Physical System'.'Sensing Device'.'CP 1'; 
                            ref :>> ownedPortAllocations =  ('CDT_System Project'::'CDT_System'::'Physical Architecture'::'Structure'::'Physical System'.'Sensing Device'.'CP 1'.'163dc662-6de6-4e4a-93be-32703a8a6bce',
                            'CDT_System Project'::'CDT_System'::'Physical Architecture'::'Structure'::'Physical System'.'Sensing Device'.'CP 1'.'ef878e19-1acd-4869-9306-8a211358d7e8'); 
                            ref :>> requiredInterfaces =  ('CDT_System Project'::'CDT_System'::'Physical Architecture'::'Interfaces'::'LORA '); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'abd8161d-1d77-44da-992d-dd5f6bd381a3' : PortAllocation
                                allocate allocatedPort ::> 'CDT_System Project'::'CDT_System'::'Physical Architecture'::'Physical Functions'::'Root Physical Function'.'Data is Retrieved'.'Provide Hit Data'.'FIP 1'
                                to allocatingPort ::> 'CDT_System Project'::'CDT_System'::'Physical Architecture'::'Structure'::'Physical System'.'Sensing Device'.'CP 2'; 
                            ref allocation '9bb0d4f7-050f-4eb6-956e-b8d196026a69' : PortAllocation
                                allocate allocatedPort ::> 'CDT_System Project'::'CDT_System'::'Physical Architecture'::'Physical Functions'::'Root Physical Function'.'Enable Monitoring'.'Look for bluetooth connect'.'FIP 2'
                                to allocatingPort ::> 'CDT_System Project'::'CDT_System'::'Physical Architecture'::'Structure'::'Physical System'.'Sensing Device'.'CP 2'; 
                            ref :>> ownedPortAllocations =  ('CDT_System Project'::'CDT_System'::'Physical Architecture'::'Structure'::'Physical System'.'Sensing Device'.'CP 2'.'abd8161d-1d77-44da-992d-dd5f6bd381a3',
                            'CDT_System Project'::'CDT_System'::'Physical Architecture'::'Structure'::'Physical System'.'Sensing Device'.'CP 2'.'9bb0d4f7-050f-4eb6-956e-b8d196026a69'); 
                        }  
                        port 'CP 3' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '9260c28e-b126-40df-bc87-96a606b0cb2f' : PortAllocation
                                allocate allocatedPort ::> 'CDT_System Project'::'CDT_System'::'Physical Architecture'::'Physical Functions'::'Root Physical Function'.'Enable Secure Collection'.'inDevice ID '
                                to allocatingPort ::> 'CDT_System Project'::'CDT_System'::'Physical Architecture'::'Structure'::'Physical System'.'Sensing Device'.'CP 3'; 
                            ref :>> ownedPortAllocations =  ('CDT_System Project'::'CDT_System'::'Physical Architecture'::'Structure'::'Physical System'.'Sensing Device'.'CP 3'.'9260c28e-b126-40df-bc87-96a606b0cb2f'); 
                        }  
                        port 'CP 4' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '1b7203de-31f5-46ae-8c4f-e3164e6f713a' : PortAllocation
                                allocate allocatedPort ::> 'CDT_System Project'::'CDT_System'::'Physical Architecture'::'Physical Functions'::'Root Physical Function'.'Device Detects Activity'.'inHit'
                                to allocatingPort ::> 'CDT_System Project'::'CDT_System'::'Physical Architecture'::'Structure'::'Physical System'.'Sensing Device'.'CP 4'; 
                            ref allocation '179e7d9e-be24-4010-9c16-776b185a6347' : PortAllocation
                                allocate allocatedPort ::> 'CDT_System Project'::'CDT_System'::'Physical Architecture'::'Physical Functions'::'Root Physical Function'.'Enable Monitoring'.'Enable Monitoring'.'inHelmut Motion'
                                to allocatingPort ::> 'CDT_System Project'::'CDT_System'::'Physical Architecture'::'Structure'::'Physical System'.'Sensing Device'.'CP 4'; 
                            ref :>> providedInterfaces =  ('CDT_System Project'::'CDT_System'::'Physical Architecture'::'Interfaces'::'Helmut to Sensor'); 
                            ref :>> ownedPortAllocations =  ('CDT_System Project'::'CDT_System'::'Physical Architecture'::'Structure'::'Physical System'.'Sensing Device'.'CP 4'.'1b7203de-31f5-46ae-8c4f-e3164e6f713a',
                            'CDT_System Project'::'CDT_System'::'Physical Architecture'::'Structure'::'Physical System'.'Sensing Device'.'CP 4'.'179e7d9e-be24-4010-9c16-776b185a6347'); 
                        }  
                        port 'CP 5' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '38c3d338-5774-42af-a2da-3a54991fe3be' : PortAllocation
                                allocate allocatedPort ::> 'CDT_System Project'::'CDT_System'::'Physical Architecture'::'Physical Functions'::'Root Physical Function'.'Recieve ID'.'inID'
                                to allocatingPort ::> 'CDT_System Project'::'CDT_System'::'Physical Architecture'::'Structure'::'Physical System'.'Sensing Device'.'CP 5'; 
                            ref allocation 'd8b61391-2880-46a4-bfe5-a5ff2cb35776' : PortAllocation
                                allocate allocatedPort ::> 'CDT_System Project'::'CDT_System'::'Physical Architecture'::'Physical Functions'::'Root Physical Function'.'Disable Secure Collection'.'FIP 1'
                                to allocatingPort ::> 'CDT_System Project'::'CDT_System'::'Physical Architecture'::'Structure'::'Physical System'.'Sensing Device'.'CP 5'; 
                            ref :>> ownedPortAllocations =  ('CDT_System Project'::'CDT_System'::'Physical Architecture'::'Structure'::'Physical System'.'Sensing Device'.'CP 5'.'38c3d338-5774-42af-a2da-3a54991fe3be',
                            'CDT_System Project'::'CDT_System'::'Physical Architecture'::'Structure'::'Physical System'.'Sensing Device'.'CP 5'.'d8b61391-2880-46a4-bfe5-a5ff2cb35776'); 
                        }  
                        state 'StateMachine 1' : StateMachine  { 
                            attribute :>> isControlOperator = false; 
                            state 'Off' : State ;  
                            state 'On' : State  { 
                                state 'Standby' : State ;  
                                state 'Monitor Activity' : State ;  
                                state 'Hit Received' : State ;  
                                transition 'db244b1f-0b24-4c48-858d-82a481e0dbb4' 
                                    first 'CDT_System Project'::'CDT_System'::'Physical Architecture'::'Structure'::'Physical System'.'Sensing Device'.'StateMachine 1'.'On'.'Standby'
                                    accept '7b17df23-af62-44ed-acba-7747c33550e5' :> 'CDT_System Project'::'CDT_System'::'Physical Architecture'::'Physical Functions'::'Root Physical Function'.'7b17df23-af62-44ed-acba-7747c33550e5'
                                    then 'CDT_System Project'::'CDT_System'::'Physical Architecture'::'Structure'::'Physical System'.'Sensing Device'.'StateMachine 1'.'On'.'Monitor Activity' {
                                }  
                                transition '9d3f53be-c781-4bb5-89ce-ce5ae8459e56' 
                                    first 'CDT_System Project'::'CDT_System'::'Physical Architecture'::'Structure'::'Physical System'.'Sensing Device'.'StateMachine 1'.'On'.'Monitor Activity'
                                    accept 'Activity' :> 'CDT_System Project'::'CDT_System'::'Physical Architecture'::'Data'::'Activity'
                                    then 'CDT_System Project'::'CDT_System'::'Physical Architecture'::'Structure'::'Physical System'.'Sensing Device'.'StateMachine 1'.'On'.'Hit Received' {
                                }  
                                transition '92c2b15b-6d88-485e-99ac-7f4549a1951a' 
                                    first 'CDT_System Project'::'CDT_System'::'Physical Architecture'::'Structure'::'Physical System'.'Sensing Device'.'StateMachine 1'.'On'.'Hit Received'
                                    do 'CDT_System Project'::'CDT_System'::'Physical Architecture'::'Physical Functions'::'Root Physical Function'.'Device alerts possible Concussion'.'Send message'
                                    then 'CDT_System Project'::'CDT_System'::'Physical Architecture'::'Structure'::'Physical System'.'Sensing Device'.'StateMachine 1'.'On'.'Monitor Activity' {
                                }  
                                transition 'f8523079-6143-4de5-b0f5-3ac04196b228' 
                                    first 'CDT_System Project'::'CDT_System'::'Physical Architecture'::'Structure'::'Physical System'.'Sensing Device'.'StateMachine 1'.'On'.'Hit Received'
                                    then 'CDT_System Project'::'CDT_System'::'Physical Architecture'::'Structure'::'Physical System'.'Sensing Device'.'StateMachine 1'.'On'.'Monitor Activity' {
                                }  
                                ref :>> referencedStates =  ('CDT_System Project'::'CDT_System'::'Physical Architecture'::'Structure'::'Physical System'.'Sensing Device'.'StateMachine 1'.'On'.'Standby',
                                'CDT_System Project'::'CDT_System'::'Physical Architecture'::'Structure'::'Physical System'.'Sensing Device'.'StateMachine 1'.'On'.'Monitor Activity',
                                'CDT_System Project'::'CDT_System'::'Physical Architecture'::'Structure'::'Physical System'.'Sensing Device'.'StateMachine 1'.'On'.'Hit Received'); 
                            }  
                            entry; then 'Off';  
                            transition '5aa760d1-c560-4044-90d2-9954af784971' 
                                first 'CDT_System Project'::'CDT_System'::'Physical Architecture'::'Structure'::'Physical System'.'Sensing Device'.'StateMachine 1'.'Off'
                                accept '7ce6b399-9ac1-4a1b-b0d8-408b5659bcd3' :> 'CDT_System Project'::'CDT_System'::'Physical Architecture'::'Physical Functions'::'Root Physical Function'.'7ce6b399-9ac1-4a1b-b0d8-408b5659bcd3'
                                then 'CDT_System Project'::'CDT_System'::'Physical Architecture'::'Structure'::'Physical System'.'Sensing Device'.'StateMachine 1'.'On'.'Standby' {
                            }  
                            transition '70434958-4a29-4afa-9ad5-6e4600b5b21c' 
                                first 'CDT_System Project'::'CDT_System'::'Physical Architecture'::'Structure'::'Physical System'.'Sensing Device'.'StateMachine 1'.'On'
                                accept '95185f6a-8c82-4db9-a48c-b51e468be017' :> 'CDT_System Project'::'CDT_System'::'Physical Architecture'::'Physical Functions'::'Root Physical Function'.'95185f6a-8c82-4db9-a48c-b51e468be017'
                                then 'CDT_System Project'::'CDT_System'::'Physical Architecture'::'Structure'::'Physical System'.'Sensing Device'.'StateMachine 1'.'Off' {
                            }  
                        }  
                        ref :>> ownedFunctionalAllocation =  ('CDT_System Project'::'CDT_System'::'Physical Architecture'::'Structure'::'Physical System'.'Sensing Device'.'67370383-11b9-4b17-9f13-6acdc0763d02',
                        'CDT_System Project'::'CDT_System'::'Physical Architecture'::'Structure'::'Physical System'.'Sensing Device'.'d96f7987-5628-46c7-a029-39a3d86f947c',
                        'CDT_System Project'::'CDT_System'::'Physical Architecture'::'Structure'::'Physical System'.'Sensing Device'.'f2765fc0-a25c-4d0a-b4bf-a71d664c4e31',
                        'CDT_System Project'::'CDT_System'::'Physical Architecture'::'Structure'::'Physical System'.'Sensing Device'.'0e75425a-cf64-4176-864c-920ce8c80b18',
                        'CDT_System Project'::'CDT_System'::'Physical Architecture'::'Structure'::'Physical System'.'Sensing Device'.'08c9cb16-f9e2-485a-9828-6f2505829275',
                        'CDT_System Project'::'CDT_System'::'Physical Architecture'::'Structure'::'Physical System'.'Sensing Device'.'7850ee0b-ef28-4650-a16f-3a06ffa20153',
                        'CDT_System Project'::'CDT_System'::'Physical Architecture'::'Structure'::'Physical System'.'Sensing Device'.'ddce45d7-13c0-4f5c-a1d1-0926397cfb48',
                        'CDT_System Project'::'CDT_System'::'Physical Architecture'::'Structure'::'Physical System'.'Sensing Device'.'d8a7671c-7cf9-4c4b-8e67-eaa7b210f95a',
                        'CDT_System Project'::'CDT_System'::'Physical Architecture'::'Structure'::'Physical System'.'Sensing Device'.'33f76bea-4ddb-49dc-8c4d-189b50d1969d',
                        'CDT_System Project'::'CDT_System'::'Physical Architecture'::'Structure'::'Physical System'.'Sensing Device'.'e1da35fc-a853-4e3f-8420-f2ab1414b968'); 
                         
                         
                        ref :>> ownedStateMachines =  ('CDT_System Project'::'CDT_System'::'Physical Architecture'::'Structure'::'Physical System'.'Sensing Device'.'StateMachine 1'); 
                    }  
                    part 'Network' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                         
                    }  
                    part 'CDT App' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation '8221817b-9f28-4926-90a2-5407be48e893' : ComponentFunctionalAllocation
                            allocate function ::> 'CDT_System Project'::'CDT_System'::'Physical Architecture'::'Physical Functions'::'Root Physical Function'.'Device alerts possible Concussion'.'Alert the Training'
                            to component ::> 'CDT_System Project'::'CDT_System'::'Physical Architecture'::'Structure'::'Physical System'.'CDT App';
                        perform 'CDT_System Project'::'CDT_System'::'Physical Architecture'::'Physical Functions'::'Root Physical Function'.'Device alerts possible Concussion'.'Alert the Training' ; 
                        allocation '5fb37973-feef-4ccf-abfb-43cebd061a6d' : ComponentFunctionalAllocation
                            allocate function ::> 'CDT_System Project'::'CDT_System'::'Physical Architecture'::'Physical Functions'::'Root Physical Function'.'Data stored'.'Data is Presented'
                            to component ::> 'CDT_System Project'::'CDT_System'::'Physical Architecture'::'Structure'::'Physical System'.'CDT App';
                        perform 'CDT_System Project'::'CDT_System'::'Physical Architecture'::'Physical Functions'::'Root Physical Function'.'Data stored'.'Data is Presented' ; 
                        allocation '8d219487-1929-49b9-88a8-f92f97ac58f7' : ComponentFunctionalAllocation
                            allocate function ::> 'CDT_System Project'::'CDT_System'::'Physical Architecture'::'Physical Functions'::'Root Physical Function'.'Generates Reports'.'Request Report to be sent'
                            to component ::> 'CDT_System Project'::'CDT_System'::'Physical Architecture'::'Structure'::'Physical System'.'CDT App';
                        perform 'CDT_System Project'::'CDT_System'::'Physical Architecture'::'Physical Functions'::'Root Physical Function'.'Generates Reports'.'Request Report to be sent' ; 
                        allocation 'ee51da49-7d2b-478b-9773-56dca9d6417c' : ComponentFunctionalAllocation
                            allocate function ::> 'CDT_System Project'::'CDT_System'::'Physical Architecture'::'Physical Functions'::'Root Physical Function'.'Enable Monitoring'.'Enable Indicated'
                            to component ::> 'CDT_System Project'::'CDT_System'::'Physical Architecture'::'Structure'::'Physical System'.'CDT App';
                        perform 'CDT_System Project'::'CDT_System'::'Physical Architecture'::'Physical Functions'::'Root Physical Function'.'Enable Monitoring'.'Enable Indicated' ; 
                        allocation '489a2630-abd6-4b45-b43c-f79875bf7b3d' : ComponentFunctionalAllocation
                            allocate function ::> 'CDT_System Project'::'CDT_System'::'Physical Architecture'::'Physical Functions'::'Root Physical Function'.'Store Profile'.'Gather Profile Data'
                            to component ::> 'CDT_System Project'::'CDT_System'::'Physical Architecture'::'Structure'::'Physical System'.'CDT App';
                        perform 'CDT_System Project'::'CDT_System'::'Physical Architecture'::'Physical Functions'::'Root Physical Function'.'Store Profile'.'Gather Profile Data' ; 
                        allocation 'e94545f9-b521-4c4b-9a59-f54c713841b6' : ComponentFunctionalAllocation
                            allocate function ::> 'CDT_System Project'::'CDT_System'::'Physical Architecture'::'Physical Functions'::'Root Physical Function'.'Create Unique IDs for Athlete'.'Initiate ID Creation'
                            to component ::> 'CDT_System Project'::'CDT_System'::'Physical Architecture'::'Structure'::'Physical System'.'CDT App';
                        perform 'CDT_System Project'::'CDT_System'::'Physical Architecture'::'Physical Functions'::'Root Physical Function'.'Create Unique IDs for Athlete'.'Initiate ID Creation' ; 
                        allocation 'fd3b5f2b-99df-4ed1-8dad-19eff5a10aab' : ComponentFunctionalAllocation
                            allocate function ::> 'CDT_System Project'::'CDT_System'::'Physical Architecture'::'Physical Functions'::'Root Physical Function'.'Data is Retrieved'.'Intitate Data Retrieval'.'Initiate Data Retrieve'
                            to component ::> 'CDT_System Project'::'CDT_System'::'Physical Architecture'::'Structure'::'Physical System'.'CDT App';
                        perform 'CDT_System Project'::'CDT_System'::'Physical Architecture'::'Physical Functions'::'Root Physical Function'.'Data is Retrieved'.'Intitate Data Retrieval'.'Initiate Data Retrieve' ; 
                        port 'To Trainer' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation 'cf9e78f4-4dfd-4d59-bd6c-625bb6bbd53d' : PortAllocation
                                allocate allocatedPort ::> 'CDT_System Project'::'CDT_System'::'Physical Architecture'::'Physical Functions'::'Root Physical Function'.'Data stored'.'Data is Presented'.'outStored Data '
                                to allocatingPort ::> 'CDT_System Project'::'CDT_System'::'Physical Architecture'::'Structure'::'Physical System'.'CDT App'.'To Trainer'; 
                            ref allocation 'c3bb07fe-17cc-4da4-9b83-22aa62896a44' : PortAllocation
                                allocate allocatedPort ::> 'CDT_System Project'::'CDT_System'::'Physical Architecture'::'Physical Functions'::'Root Physical Function'.'Enable Monitoring'.'Enable Indicated'.'outEnable Signal'
                                to allocatingPort ::> 'CDT_System Project'::'CDT_System'::'Physical Architecture'::'Structure'::'Physical System'.'CDT App'.'To Trainer'; 
                            ref allocation 'ba805ff9-3cf3-4d2f-ab77-bf07d7425e96' : PortAllocation
                                allocate allocatedPort ::> 'CDT_System Project'::'CDT_System'::'Physical Architecture'::'Physical Functions'::'Root Physical Function'.'Device alerts possible Concussion'.'Alert the Training'.'outConcussion Alert to Trainer'
                                to allocatingPort ::> 'CDT_System Project'::'CDT_System'::'Physical Architecture'::'Structure'::'Physical System'.'CDT App'.'To Trainer'; 
                            ref allocation '116e99cf-c7ef-4919-bed2-44e1847ff54f' : PortAllocation
                                allocate allocatedPort ::> 'CDT_System Project'::'CDT_System'::'Physical Architecture'::'Physical Functions'::'Root Physical Function'.'Create Unique IDs for Athlete'.'Initiate ID Creation'.'inID'
                                to allocatingPort ::> 'CDT_System Project'::'CDT_System'::'Physical Architecture'::'Structure'::'Physical System'.'CDT App'.'To Trainer'; 
                            ref allocation '38e36f78-c7d7-4abf-9953-5b498b65afbb' : PortAllocation
                                allocate allocatedPort ::> 'CDT_System Project'::'CDT_System'::'Physical Architecture'::'Physical Functions'::'Root Physical Function'.'Generates Reports'.'Request Report to be sent'.'inExecute Policy'
                                to allocatingPort ::> 'CDT_System Project'::'CDT_System'::'Physical Architecture'::'Structure'::'Physical System'.'CDT App'.'To Trainer'; 
                            ref allocation '4dd81c9a-0f24-4190-a100-850a6efa95bd' : PortAllocation
                                allocate allocatedPort ::> 'CDT_System Project'::'CDT_System'::'Physical Architecture'::'Physical Functions'::'Root Physical Function'.'Store Profile'.'Gather Profile Data'.'inAthlete Profile'
                                to allocatingPort ::> 'CDT_System Project'::'CDT_System'::'Physical Architecture'::'Structure'::'Physical System'.'CDT App'.'To Trainer'; 
                            ref :>> ownedPortAllocations =  ('CDT_System Project'::'CDT_System'::'Physical Architecture'::'Structure'::'Physical System'.'CDT App'.'To Trainer'.'cf9e78f4-4dfd-4d59-bd6c-625bb6bbd53d',
                            'CDT_System Project'::'CDT_System'::'Physical Architecture'::'Structure'::'Physical System'.'CDT App'.'To Trainer'.'c3bb07fe-17cc-4da4-9b83-22aa62896a44',
                            'CDT_System Project'::'CDT_System'::'Physical Architecture'::'Structure'::'Physical System'.'CDT App'.'To Trainer'.'ba805ff9-3cf3-4d2f-ab77-bf07d7425e96',
                            'CDT_System Project'::'CDT_System'::'Physical Architecture'::'Structure'::'Physical System'.'CDT App'.'To Trainer'.'116e99cf-c7ef-4919-bed2-44e1847ff54f',
                            'CDT_System Project'::'CDT_System'::'Physical Architecture'::'Structure'::'Physical System'.'CDT App'.'To Trainer'.'38e36f78-c7d7-4abf-9953-5b498b65afbb',
                            'CDT_System Project'::'CDT_System'::'Physical Architecture'::'Structure'::'Physical System'.'CDT App'.'To Trainer'.'4dd81c9a-0f24-4190-a100-850a6efa95bd'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                        }  
                        port 'CP 3' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '4fcf52a1-0682-4e0e-a022-d82e065d3007' : PortAllocation
                                allocate allocatedPort ::> 'CDT_System Project'::'CDT_System'::'Physical Architecture'::'Physical Functions'::'Root Physical Function'.'Store Profile'.'Gather Profile Data'.'FOP 1'
                                to allocatingPort ::> 'CDT_System Project'::'CDT_System'::'Physical Architecture'::'Structure'::'Physical System'.'CDT App'.'CP 3'; 
                            ref allocation '62394fa5-dc76-4e5a-b4a4-4ff8ae85731b' : PortAllocation
                                allocate allocatedPort ::> 'CDT_System Project'::'CDT_System'::'Physical Architecture'::'Physical Functions'::'Root Physical Function'.'Device alerts possible Concussion'.'Alert the Training'.'FIP 1'
                                to allocatingPort ::> 'CDT_System Project'::'CDT_System'::'Physical Architecture'::'Structure'::'Physical System'.'CDT App'.'CP 3'; 
                            ref allocation 'd3dfb37c-a83e-4a5f-ad6d-714ce28deceb' : PortAllocation
                                allocate allocatedPort ::> 'CDT_System Project'::'CDT_System'::'Physical Architecture'::'Physical Functions'::'Root Physical Function'.'Data is Retrieved'.'Intitate Data Retrieval'.'Initiate Data Retrieve'.'outRecorded Data'
                                to allocatingPort ::> 'CDT_System Project'::'CDT_System'::'Physical Architecture'::'Structure'::'Physical System'.'CDT App'.'CP 3'; 
                            ref allocation 'a80f0495-f8ae-4487-82be-b2858d27fe97' : PortAllocation
                                allocate allocatedPort ::> 'CDT_System Project'::'CDT_System'::'Physical Architecture'::'Physical Functions'::'Root Physical Function'.'Enable Monitoring'.'Enable Indicated'.'FIP 1'
                                to allocatingPort ::> 'CDT_System Project'::'CDT_System'::'Physical Architecture'::'Structure'::'Physical System'.'CDT App'.'CP 3'; 
                            ref allocation '0222aff0-391c-4f38-9b17-13295e3e3c74' : PortAllocation
                                allocate allocatedPort ::> 'CDT_System Project'::'CDT_System'::'Physical Architecture'::'Physical Functions'::'Root Physical Function'.'Data stored'.'Data is Presented'.'FIP 1'
                                to allocatingPort ::> 'CDT_System Project'::'CDT_System'::'Physical Architecture'::'Structure'::'Physical System'.'CDT App'.'CP 3'; 
                            ref allocation 'a9f0bea1-5738-4194-b64d-a56e8314834b' : PortAllocation
                                allocate allocatedPort ::> 'CDT_System Project'::'CDT_System'::'Physical Architecture'::'Physical Functions'::'Root Physical Function'.'Generates Reports'.'Request Report to be sent'.'FOP 1'
                                to allocatingPort ::> 'CDT_System Project'::'CDT_System'::'Physical Architecture'::'Structure'::'Physical System'.'CDT App'.'CP 3'; 
                            ref allocation '489ead20-9505-47a3-9fdb-2036d03cdacf' : PortAllocation
                                allocate allocatedPort ::> 'CDT_System Project'::'CDT_System'::'Physical Architecture'::'Physical Functions'::'Root Physical Function'.'Create Unique IDs for Athlete'.'Initiate ID Creation'.'FOP 1'
                                to allocatingPort ::> 'CDT_System Project'::'CDT_System'::'Physical Architecture'::'Structure'::'Physical System'.'CDT App'.'CP 3'; 
                            ref :>> ownedPortAllocations =  ('CDT_System Project'::'CDT_System'::'Physical Architecture'::'Structure'::'Physical System'.'CDT App'.'CP 3'.'4fcf52a1-0682-4e0e-a022-d82e065d3007',
                            'CDT_System Project'::'CDT_System'::'Physical Architecture'::'Structure'::'Physical System'.'CDT App'.'CP 3'.'62394fa5-dc76-4e5a-b4a4-4ff8ae85731b',
                            'CDT_System Project'::'CDT_System'::'Physical Architecture'::'Structure'::'Physical System'.'CDT App'.'CP 3'.'d3dfb37c-a83e-4a5f-ad6d-714ce28deceb',
                            'CDT_System Project'::'CDT_System'::'Physical Architecture'::'Structure'::'Physical System'.'CDT App'.'CP 3'.'a80f0495-f8ae-4487-82be-b2858d27fe97',
                            'CDT_System Project'::'CDT_System'::'Physical Architecture'::'Structure'::'Physical System'.'CDT App'.'CP 3'.'0222aff0-391c-4f38-9b17-13295e3e3c74',
                            'CDT_System Project'::'CDT_System'::'Physical Architecture'::'Structure'::'Physical System'.'CDT App'.'CP 3'.'a9f0bea1-5738-4194-b64d-a56e8314834b',
                            'CDT_System Project'::'CDT_System'::'Physical Architecture'::'Structure'::'Physical System'.'CDT App'.'CP 3'.'489ead20-9505-47a3-9fdb-2036d03cdacf'); 
                        }  
                        ref :>> ownedFunctionalAllocation =  ('CDT_System Project'::'CDT_System'::'Physical Architecture'::'Structure'::'Physical System'.'CDT App'.'8221817b-9f28-4926-90a2-5407be48e893',
                        'CDT_System Project'::'CDT_System'::'Physical Architecture'::'Structure'::'Physical System'.'CDT App'.'5fb37973-feef-4ccf-abfb-43cebd061a6d',
                        'CDT_System Project'::'CDT_System'::'Physical Architecture'::'Structure'::'Physical System'.'CDT App'.'8d219487-1929-49b9-88a8-f92f97ac58f7',
                        'CDT_System Project'::'CDT_System'::'Physical Architecture'::'Structure'::'Physical System'.'CDT App'.'ee51da49-7d2b-478b-9773-56dca9d6417c',
                        'CDT_System Project'::'CDT_System'::'Physical Architecture'::'Structure'::'Physical System'.'CDT App'.'489a2630-abd6-4b45-b43c-f79875bf7b3d',
                        'CDT_System Project'::'CDT_System'::'Physical Architecture'::'Structure'::'Physical System'.'CDT App'.'e94545f9-b521-4c4b-9a59-f54c713841b6',
                        'CDT_System Project'::'CDT_System'::'Physical Architecture'::'Structure'::'Physical System'.'CDT App'.'fd3b5f2b-99df-4ed1-8dad-19eff5a10aab'); 
                         
                         
                    }  
                    part 'Bluetooth' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation 'e2d63008-f92e-4578-97c2-965db70de6ea' : ComponentFunctionalAllocation
                            allocate function ::> 'CDT_System Project'::'CDT_System'::'Physical Architecture'::'Physical Functions'::'Root Physical Function'.'Data is Retrieved'.'Request the Data '
                            to component ::> 'CDT_System Project'::'CDT_System'::'Physical Architecture'::'Structure'::'Physical System'.'Bluetooth';
                        perform 'CDT_System Project'::'CDT_System'::'Physical Architecture'::'Physical Functions'::'Root Physical Function'.'Data is Retrieved'.'Request the Data ' ; 
                        allocation '7e53ee1a-a873-4601-ab73-613b34901186' : ComponentFunctionalAllocation
                            allocate function ::> 'CDT_System Project'::'CDT_System'::'Physical Architecture'::'Physical Functions'::'Root Physical Function'.'Enable Monitoring'.'Enable Bluetoth Connect'
                            to component ::> 'CDT_System Project'::'CDT_System'::'Physical Architecture'::'Structure'::'Physical System'.'Bluetooth';
                        perform 'CDT_System Project'::'CDT_System'::'Physical Architecture'::'Physical Functions'::'Root Physical Function'.'Enable Monitoring'.'Enable Bluetoth Connect' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '17a5cea3-a286-43d6-875c-631177de594f' : PortAllocation
                                allocate allocatedPort ::> 'CDT_System Project'::'CDT_System'::'Physical Architecture'::'Physical Functions'::'Root Physical Function'.'Data is Retrieved'.'Request the Data '.'FOP 1'
                                to allocatingPort ::> 'CDT_System Project'::'CDT_System'::'Physical Architecture'::'Structure'::'Physical System'.'Bluetooth'.'CP 1'; 
                            ref allocation '0772de7c-993e-456a-9abd-ecbbab1f0b07' : PortAllocation
                                allocate allocatedPort ::> 'CDT_System Project'::'CDT_System'::'Physical Architecture'::'Physical Functions'::'Root Physical Function'.'Enable Monitoring'.'Enable Bluetoth Connect'.'FOP 1'
                                to allocatingPort ::> 'CDT_System Project'::'CDT_System'::'Physical Architecture'::'Structure'::'Physical System'.'Bluetooth'.'CP 1'; 
                            ref :>> ownedPortAllocations =  ('CDT_System Project'::'CDT_System'::'Physical Architecture'::'Structure'::'Physical System'.'Bluetooth'.'CP 1'.'17a5cea3-a286-43d6-875c-631177de594f',
                            'CDT_System Project'::'CDT_System'::'Physical Architecture'::'Structure'::'Physical System'.'Bluetooth'.'CP 1'.'0772de7c-993e-456a-9abd-ecbbab1f0b07'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                        }  
                        ref :>> ownedFunctionalAllocation =  ('CDT_System Project'::'CDT_System'::'Physical Architecture'::'Structure'::'Physical System'.'Bluetooth'.'e2d63008-f92e-4578-97c2-965db70de6ea',
                        'CDT_System Project'::'CDT_System'::'Physical Architecture'::'Structure'::'Physical System'.'Bluetooth'.'7e53ee1a-a873-4601-ab73-613b34901186'); 
                         
                         
                    }  
                    part 'Helmet' : PhysicalComponent { 
                        doc /*


                        <p>A helmet is a form of protective gear worn to protect the head from injury. Helmets are a common piece of safety equipment in many sports, and are also used by military personnel, construction workers and cyclists. The most common form of helmet is made of a hard, durable outer shell and a soft, cushioned inner liner. The outer shell is designed to absorb and distribute the force of an impact, while the inner liner provides cushioning and shock absorption. The helmet also typically has a chin strap and straps to keep the helmet snugly in place. <sup>1</sup></p>

                        <p>In addition to providing protection from physical impacts, helmets are also designed to protect the head from exposure to hazardous materials. This includes protection from heat, cold, fire, and chemicals. Helmets come in a variety of shapes and sizes and can be made from different materials, including plastic, Kevlar, carbon fiber, and fiberglass. <sup>2</sup></p>

                        <p>References:</p>
                        <p>1. "Helmet Safety," The American Academy of Pediatrics, February 2015, <em>https://www.aap.org/en-us/about-the-
                        */ 
                        attribute :>> nature = PhysicalComponentNature::NODE; 
                        attribute :>> kind = PhysicalComponentKind::UNSET; 
                        attribute :>> isAbstract = false; 
                        attribute :>> isActor = false; 
                        attribute :>> isHuman = false; 
                        interface '17a882c6-874d-47e9-aa4c-49d3cf825348' : PhysicalLink 
                            connect sourcePhysicalPort ::> 'CDT_System Project'::'CDT_System'::'Physical Architecture'::'Structure'::'Physical System'.'Helmet'.'Sensor'.'PP 1'
                            to targetPhysicalPort ::> 'CDT_System Project'::'CDT_System'::'Physical Architecture'::'Structure'::'Physical System'.'Helmet'.'ID'.'PP 1' {
                            attribute :>> interfaceName = "Physical"; 
                             
                        }  
                        interface 'bc095b8c-942f-4d94-92d7-f77914c9fd34' : PhysicalLink 
                            connect sourcePhysicalPort ::> 'CDT_System Project'::'CDT_System'::'Physical Architecture'::'Structure'::'Physical System'.'Helmet'.'PP 3'
                            to targetPhysicalPort ::> 'CDT_System Project'::'CDT_System'::'Physical Architecture'::'Structure'::'Physical System'.'Helmet'.'Sensor'.'PP 4' {
                            attribute :>> interfaceName = "M - H to S"; 
                             
                        }  
                        part 'Sensor' : PhysicalComponent { 
                            doc /*
                            <title></title>
                            <h1>Sensor</h1>

                            <p>A sensor is a device that measures specific physical properties or changes in the environment and converts them into signals that can be interpreted by an observer or a computer system. Sensors are used in various fields including engineering, science, medicine, and automation.</p>

                            <p>Sensors can detect and measure a wide range of parameters such as temperature, pressure, humidity, light intensity, motion, proximity, acceleration, and more. They are designed to capture and transmit data accurately and efficiently, enabling continuous monitoring and control of different systems and processes.</p>

                            <p>There are various types of sensors available, each designed for a specific purpose. Some common sensor types include:</p>

                            <ol>
                            	<li><strong>Temperature sensor:</strong> measures temperature changes.</li>
                            	<li><strong>Pressure sensor:</strong> measures changes in pressure.</li>
                            	<li><strong>Proximity sensor:</strong> detects the presence or absence of objects within a certain range.</li>
                            	<li><strong>Accelerometer:</strong> measures acceleration forces.</li>
                            	<li><strong>Light sensor:</strong> measures light intensity.</li>
                            	<li><strong>Humidity sensor:</strong> measures humidity levels.</li>
                            </ol>

                            <p>Sensors are crucial components in many electronic systems, from everyday devices like smartphones and automobiles, to complex industrial automation systems. They enable data collection, analysis, and decision-making in real-time.</p>

                            <p>For further information about sensors and their applications, you can refer to the following resources:</p>

                            <ul>
                            	<li><a href="https://www.sciencedirect.com/science/article/pii/S2405896318321972">Sensor Technologies: A Review</a></li>
                            	<li><a href="https://www.sensorsmag.com/sensors-101/types-sensors">Sensors Magazine: Types of Sensors</a></li>
                            	<li><a href="https://en.wikipedia.org/wiki/Sensor">Wikipedia: Sensor</a></li>
                            </ul>

                            */ 
                            attribute :>> nature = PhysicalComponentNature::NODE; 
                            attribute :>> kind = PhysicalComponentKind::UNSET; 
                            attribute :>> isAbstract = false; 
                            attribute :>> isActor = false; 
                            attribute :>> isHuman = false; 
                            attribute 'Mass' : PropertyValueGroup { 
                                doc /*
                                <p>The Mass of the related object.</p>

                                */ 
                                attribute :>> summary = "Mass of Related Object"; 
                                attribute 'Value' : FloatPropertyValue  = 0.1;  
                                attribute 'Unis' : StringPropertyValue  = 'Kg';  
                                ref :>> ownedPropertyValues =  ('CDT_System Project'::'CDT_System'::'Physical Architecture'::'Structure'::'Physical System'.'Helmet'.'Sensor'.'Mass'.'Value',
                                'CDT_System Project'::'CDT_System'::'Physical Architecture'::'Structure'::'Physical System'.'Helmet'.'Sensor'.'Mass'.'Unis'); 
                            }  
                            attribute 'Cost' : PropertyValueGroup { 
                                attribute 'Units' : StringPropertyValue  = '$';  
                                attribute 'Value' : FloatPropertyValue  = 20.0;  
                                ref :>> ownedPropertyValues =  ('CDT_System Project'::'CDT_System'::'Physical Architecture'::'Structure'::'Physical System'.'Helmet'.'Sensor'.'Cost'.'Units',
                                'CDT_System Project'::'CDT_System'::'Physical Architecture'::'Structure'::'Physical System'.'Helmet'.'Sensor'.'Cost'.'Value'); 
                            }  
                            port 'PP 1' : PhysicalPort { 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                                ref allocation 'aaaa2050-2b21-472f-baf2-a208e257604e' : ComponentPortAllocation
                                    allocate allocatedPort ::> 'CDT_System Project'::'CDT_System'::'Physical Architecture'::'Structure'::'Physical System'.'Helmet'.'Sensor'.'PP 1'
                                    to allocatingPort ::> 'CDT_System Project'::'CDT_System'::'Physical Architecture'::'Structure'::'Physical System'.'Sensing Device'.'CP 3'; 
                                ref :>> ownedComponentPortAllocations =  ('CDT_System Project'::'CDT_System'::'Physical Architecture'::'Structure'::'Physical System'.'Helmet'.'Sensor'.'PP 1'.'aaaa2050-2b21-472f-baf2-a208e257604e'); 
                            }  
                            port 'PP 2' : PhysicalPort { 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                                ref allocation '10e69ae6-568a-4b2c-b718-5f39617d5b4b' : ComponentPortAllocation
                                    allocate allocatedPort ::> 'CDT_System Project'::'CDT_System'::'Physical Architecture'::'Structure'::'Physical System'.'Helmet'.'Sensor'.'PP 2'
                                    to allocatingPort ::> 'CDT_System Project'::'CDT_System'::'Physical Architecture'::'Structure'::'Physical System'.'Sensing Device'.'CP 1'; 
                                ref :>> ownedComponentPortAllocations =  ('CDT_System Project'::'CDT_System'::'Physical Architecture'::'Structure'::'Physical System'.'Helmet'.'Sensor'.'PP 2'.'10e69ae6-568a-4b2c-b718-5f39617d5b4b'); 
                            }  
                            port 'To IPAD' : PhysicalPort { 
                                doc /*
                                <p>PP3 Description</p>

                                */ 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                                ref allocation 'e0e9c8d4-fd7a-4d02-85ef-a43989bbbe8c' : ComponentPortAllocation
                                    allocate allocatedPort ::> 'CDT_System Project'::'CDT_System'::'Physical Architecture'::'Structure'::'Physical System'.'Helmet'.'Sensor'.'To IPAD'
                                    to allocatingPort ::> 'CDT_System Project'::'CDT_System'::'Physical Architecture'::'Structure'::'Physical System'.'Sensing Device'.'CP 2'; 
                                attribute 'Communication Type' : StringPropertyValue  = 'Bluetooth';  
                                ref :>> ownedComponentPortAllocations =  ('CDT_System Project'::'CDT_System'::'Physical Architecture'::'Structure'::'Physical System'.'Helmet'.'Sensor'.'To IPAD'.'e0e9c8d4-fd7a-4d02-85ef-a43989bbbe8c'); 
                                ref :>> appliedPropertyValues =  ('CDT_System Project'::'CDT_System'::'Physical Architecture'::'Structure'::'Physical System'.'Helmet'.'Sensor'.'To IPAD'.'Communication Type'); 
                                ref :>> ownedPropertyValues =  ('CDT_System Project'::'CDT_System'::'Physical Architecture'::'Structure'::'Physical System'.'Helmet'.'Sensor'.'To IPAD'.'Communication Type'); 
                            }  
                            port 'PP 4' : PhysicalPort { 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                                ref allocation '72dea18c-b319-41e5-a56b-ac32a20c1ff5' : ComponentPortAllocation
                                    allocate allocatedPort ::> 'CDT_System Project'::'CDT_System'::'Physical Architecture'::'Structure'::'Physical System'.'Helmet'.'Sensor'.'PP 4'
                                    to allocatingPort ::> 'CDT_System Project'::'CDT_System'::'Physical Architecture'::'Structure'::'Physical System'.'Sensing Device'.'CP 4'; 
                                ref :>> ownedComponentPortAllocations =  ('CDT_System Project'::'CDT_System'::'Physical Architecture'::'Structure'::'Physical System'.'Helmet'.'Sensor'.'PP 4'.'72dea18c-b319-41e5-a56b-ac32a20c1ff5'); 
                            }  
                            port 'PP 5' : PhysicalPort { 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                                ref allocation '3c5955d7-361d-4bb7-b9e6-a5ae56738906' : ComponentPortAllocation
                                    allocate allocatedPort ::> 'CDT_System Project'::'CDT_System'::'Physical Architecture'::'Structure'::'Physical System'.'Helmet'.'Sensor'.'PP 5'
                                    to allocatingPort ::> 'CDT_System Project'::'CDT_System'::'Physical Architecture'::'Structure'::'Physical System'.'Sensing Device'.'CP 5'; 
                                ref :>> ownedComponentPortAllocations =  ('CDT_System Project'::'CDT_System'::'Physical Architecture'::'Structure'::'Physical System'.'Helmet'.'Sensor'.'PP 5'.'3c5955d7-361d-4bb7-b9e6-a5ae56738906'); 
                            }  
                            state 'StateMachine 1' : StateMachine  { 
                                attribute :>> isControlOperator = false; 
                            }  
                            attribute 'Power Source' : StringPropertyValue  = 'LI Rechargeable Battery';  
                            attribute 'Color' : StringPropertyValue  = 'Black';  
                            ref :>> appliedPropertyValues =  ('CDT_System Project'::'CDT_System'::'Physical Architecture'::'Structure'::'Physical System'.'Helmet'.'Sensor'.'Power Source',
                            'CDT_System Project'::'CDT_System'::'Physical Architecture'::'Structure'::'Physical System'.'Helmet'.'Sensor'.'Color'); 
                            ref :>> ownedPropertyValueGroups =  ('CDT_System Project'::'CDT_System'::'Physical Architecture'::'Structure'::'Physical System'.'Helmet'.'Sensor'.'Mass',
                            'CDT_System Project'::'CDT_System'::'Physical Architecture'::'Structure'::'Physical System'.'Helmet'.'Sensor'.'Cost'); 
                            ref :>> appliedPropertyValueGroups =  ('CDT_System Project'::'CDT_System'::'Physical Architecture'::'Structure'::'Physical System'.'Helmet'.'Sensor'.'Mass',
                            'CDT_System Project'::'CDT_System'::'Physical Architecture'::'Structure'::'Physical System'.'Helmet'.'Sensor'.'Cost'); 
                            ref :>> ownedStateMachines =  ('CDT_System Project'::'CDT_System'::'Physical Architecture'::'Structure'::'Physical System'.'Helmet'.'Sensor'.'StateMachine 1'); 
                            ref :>> ownedPropertyValues =  ('CDT_System Project'::'CDT_System'::'Physical Architecture'::'Structure'::'Physical System'.'Helmet'.'Sensor'.'Power Source',
                            'CDT_System Project'::'CDT_System'::'Physical Architecture'::'Structure'::'Physical System'.'Helmet'.'Sensor'.'Color'); 
                            allocation '627c9520-5f7c-443a-8f4b-cadc19452bee' : PartDeploymentLink
                                allocate deployed ::> 'CDT_System Project'::'CDT_System'::'Physical Architecture'::'Structure'::'Physical System'.'Helmet'.'Sensor'
                                to deploying ::> 'CDT_System Project'::'CDT_System'::'Physical Architecture'::'Structure'::'Physical System'.'Sensing Device'; 
                        }  
                        part 'ID' : PhysicalComponent { 
                            attribute :>> nature = PhysicalComponentNature::NODE; 
                            attribute :>> kind = PhysicalComponentKind::UNSET; 
                            attribute :>> isAbstract = false; 
                            attribute :>> isActor = false; 
                            attribute :>> isHuman = false; 
                            port 'PP 1' : PhysicalPort { 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                                ref allocation 'b45b918a-8258-4afa-9c55-36be5af8c160' : ComponentPortAllocation
                                    allocate allocatedPort ::> 'CDT_System Project'::'CDT_System'::'Physical Architecture'::'Structure'::'Physical System'.'Helmet'.'ID'.'PP 1'
                                    to allocatingPort ::> 'CDT_System Project'::'CDT_System'::'Physical Architecture'::'Structure'::'Physical System'.'ID Device'.'CP 1'; 
                                ref :>> ownedComponentPortAllocations =  ('CDT_System Project'::'CDT_System'::'Physical Architecture'::'Structure'::'Physical System'.'Helmet'.'ID'.'PP 1'.'b45b918a-8258-4afa-9c55-36be5af8c160'); 
                            }  
                            port 'PP 4' : PhysicalPort { 
                                attribute :>> isDerived = false; 
                                attribute :>> aggregationKind = AggregationKind::UNSET; 
                                attribute :>> isFinal = false; 
                                attribute :>> isPartOfKey = false; 
                                attribute :>> isMaxInclusive = false; 
                                attribute :>> isUnique = false; 
                                attribute :>> isMinInclusive = false; 
                                attribute :>> isReadOnly = false; 
                                attribute :>> isStatic = false; 
                                attribute :>> isOrdered = false; 
                                attribute :>> isAbstract = false; 
                            }  
                            allocation 'debd0350-54b2-4e2b-9409-91e6b67d5d73' : PartDeploymentLink
                                allocate deployed ::> 'CDT_System Project'::'CDT_System'::'Physical Architecture'::'Structure'::'Physical System'.'Helmet'.'ID'
                                to deploying ::> 'CDT_System Project'::'CDT_System'::'Physical Architecture'::'Structure'::'Physical System'.'ID Device'; 
                        }  
                        port 'PP 3' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '92a467e5-7eed-4a36-9c04-388606d36aff' : ComponentPortAllocation
                                allocate allocatedPort ::> 'CDT_System Project'::'CDT_System'::'Physical Architecture'::'Structure'::'Physical System'.'Helmet'.'PP 3'
                                to allocatingPort ::> 'CDT_System Project'::'CDT_System'::'Physical Architecture'::'Structure'::'Physical System'.'Helmet'.'CP 1'; 
                            ref allocation '933542a8-5ec6-4473-918b-6dfe39f99a62' : ComponentPortAllocation
                                allocate allocatedPort ::> 'CDT_System Project'::'CDT_System'::'Physical Architecture'::'Structure'::'Physical System'.'Helmet'.'PP 3'
                                to allocatingPort ::> 'CDT_System Project'::'CDT_System'::'Physical Architecture'::'Structure'::'Physical System'.'Helmet'.'CP 3'; 
                            ref :>> ownedComponentPortAllocations =  ('CDT_System Project'::'CDT_System'::'Physical Architecture'::'Structure'::'Physical System'.'Helmet'.'PP 3'.'92a467e5-7eed-4a36-9c04-388606d36aff',
                            'CDT_System Project'::'CDT_System'::'Physical Architecture'::'Structure'::'Physical System'.'Helmet'.'PP 3'.'933542a8-5ec6-4473-918b-6dfe39f99a62'); 
                        }  
                        ref :>> ownedPhysicalLinks =  ('CDT_System Project'::'CDT_System'::'Physical Architecture'::'Structure'::'Physical System'.'Helmet'.'17a882c6-874d-47e9-aa4c-49d3cf825348',
                        'CDT_System Project'::'CDT_System'::'Physical Architecture'::'Structure'::'Physical System'.'Helmet'.'bc095b8c-942f-4d94-92d7-f77914c9fd34'); 
                        ref :>> ownedPhysicalComponents =  ('CDT_System Project'::'CDT_System'::'Physical Architecture'::'Structure'::'Physical System'.'Helmet'.'Sensor',
                        'CDT_System Project'::'CDT_System'::'Physical Architecture'::'Structure'::'Physical System'.'Helmet'.'ID'); 
                        allocation '2345f7df-d02a-4eb0-b62e-3655ecfddc6e' : PartDeploymentLink
                            allocate deployed ::> 'CDT_System Project'::'CDT_System'::'Physical Architecture'::'Structure'::'Physical System'.'Helmet'
                            to deploying ::> 'CDT_System Project'::'CDT_System'::'Physical Architecture'::'Structure'::'Physical System'.'Helmet'; 
                    }  
                    part 'LORAWAN Gateway' : PhysicalComponent { 
                        doc /*
                        <!DOCTYPE html>
                        <html>
                        <head>
                          <title>LORAWAN Gateway - Brief Description</title>
                        </head>
                        <body>

                        <h1>LORAWAN Gateway - Brief Description</h1>

                        <p>A LORAWAN Gateway, also known as LORA Gateway or LORA Base Station, is a device that acts as a bridge between LORAWAN (Long Range Wide Area Network) sensor devices and the internet. It is a crucial component of the LORAWAN network infrastructure and plays a vital role in enabling the communication and transmission of data from LORAWAN end nodes to the central network server.</p>

                        <p>The LORAWAN Gateway receives signals from LORAWAN end devices, such as sensors or devices equipped with LORAWAN modules, and forwards these signals to the LORAWAN network server over an IP-based connection. It acts as a centralized entry point for the LORAWAN network, enabling the aggregation and routing of data from multiple end devices.</p>

                        <p>Typically, a LORAWAN Gateway operates on one or more dedicated frequencies within the license-free sub-gigahertz ISM (Industrial, Scientific, Medical) radio bands. It receives and demodulates signals from LORAWAN end devices using the LORA modulation scheme, which allows for long-range communication with low power consumption. The demodulated data is then forwarded to the LORAWAN network server via an internet connection, such as Ethernet or cellular network.</p>

                        <p>Some key features of a LORAWAN Gateway include:</p>
                        <ul>
                          <li>Multiple channel support to accommodate simultaneous communication with various LORAWAN end devices</li>
                          <li>Support for different LORA spreading factors to ensure efficient data transmission</li>
                          <li>Integration with network servers using LORAWAN protocol</li>
                          <li>Various physical interfaces for connectivity, such as Ethernet, Wi-Fi, or cellular</li>
                          <li>Ability to handle large-scale deployments by supporting multiple gateways in a network</li>
                        </ul>

                        <p>LORAWAN Gateways are essential for establishing wide-area LORAWAN networks that enable long-range, low-power communication for various Internet of Things (IoT) applications. These gateways serve as the primary bridge between end devices and the central network infrastructure, allowing seamless data transfer over long distances.</p>
                          
                        <p>References:</p>
                        <ol>
                          <li>
                            "LORAWAN Gateway". The Things Network. Retrieved from <a href="https://www.thethingsnetwork.org/docs/gateways/">https://www.thethingsnetwork.org/docs/gateways/</a>
                          </li>
                          <li>
                            "Gateways, ProudGateways & Antennas". LORA Alliance. Retrieved from <a href="https://lora-alliance.org/about-lorawan/lorawan-gateway/">https://lora-alliance.org/about-lorawan/lorawan-gateway/</a>
                          </li>
                        </ol>

                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        constraint '19554a79-1752-4709-815b-854da02965f2' : CapellaConstraint { 
                            language "capella:linkedText" /*  */
                            ref :>> constrainedElements =  ('CDT_System Project'::'CDT_System'::'Physical Architecture'::'Structure'::'Physical System'.'LORAWAN Gateway');
                            
                        } 
                        port 'To LORA Nodes' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '245a2d19-6ab1-465e-aad4-b3c93ee2ad7b' : ComponentPortAllocation
                                allocate allocatedPort ::> 'CDT_System Project'::'CDT_System'::'Physical Architecture'::'Structure'::'Physical System'.'LORAWAN Gateway'.'To LORA Nodes'
                                to allocatingPort ::> 'CDT_System Project'::'CDT_System'::'Physical Architecture'::'Structure'::'Physical System'.'Helium RS Connect'.'From LORAWAN Sensors'; 
                            ref :>> ownedComponentPortAllocations =  ('CDT_System Project'::'CDT_System'::'Physical Architecture'::'Structure'::'Physical System'.'LORAWAN Gateway'.'To LORA Nodes'.'245a2d19-6ab1-465e-aad4-b3c93ee2ad7b'); 
                        }  
                        port 'To CAT 5' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '766d2861-c88b-40d2-9d21-b9430864c59c' : ComponentPortAllocation
                                allocate allocatedPort ::> 'CDT_System Project'::'CDT_System'::'Physical Architecture'::'Structure'::'Physical System'.'LORAWAN Gateway'.'To CAT 5'
                                to allocatingPort ::> 'CDT_System Project'::'CDT_System'::'Physical Architecture'::'Structure'::'Physical System'.'Helium RS Connect'.'To Cloud Console'; 
                            ref :>> ownedComponentPortAllocations =  ('CDT_System Project'::'CDT_System'::'Physical Architecture'::'Structure'::'Physical System'.'LORAWAN Gateway'.'To CAT 5'.'766d2861-c88b-40d2-9d21-b9430864c59c'); 
                        }  
                        port 'To WIFI' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '7a02782c-c2a4-4a86-b332-5ff27df260cd' : ComponentPortAllocation
                                allocate allocatedPort ::> 'CDT_System Project'::'CDT_System'::'Physical Architecture'::'Structure'::'Physical System'.'LORAWAN Gateway'.'To WIFI'
                                to allocatingPort ::> 'CDT_System Project'::'CDT_System'::'Physical Architecture'::'Structure'::'Physical System'.'Helium RS Connect'.'To Cloud Console'; 
                            ref :>> ownedComponentPortAllocations =  ('CDT_System Project'::'CDT_System'::'Physical Architecture'::'Structure'::'Physical System'.'LORAWAN Gateway'.'To WIFI'.'7a02782c-c2a4-4a86-b332-5ff27df260cd'); 
                        }  
                        ref :>> ownedConstraints =  ('CDT_System Project'::'CDT_System'::'Physical Architecture'::'Structure'::'Physical System'.'LORAWAN Gateway'.'19554a79-1752-4709-815b-854da02965f2'); 
                        allocation 'b3acb5e6-aa4a-42c0-a270-2fadc0fd6c9c' : PartDeploymentLink
                            allocate deployed ::> 'CDT_System Project'::'CDT_System'::'Physical Architecture'::'Structure'::'Physical System'.'LORAWAN Gateway'
                            to deploying ::> 'CDT_System Project'::'CDT_System'::'Physical Architecture'::'Structure'::'Physical System'.'Helium RS Connect'; 
                    }  
                    part 'Modem' : PhysicalComponent { 
                        doc /*
                        <!DOCTYPE html>
                        <html>
                        <head>
                        <title>Modem Description</title>
                        <style>
                        body {
                            font-family: Arial, sans-serif;
                        }
                        h1 {
                            color: #333333;
                            font-size: 24px;
                            text-decoration: underline;
                        }
                        p {
                            color: #666666;
                            font-size: 16px;
                            line-height: 1.6;
                        }
                        </style>
                        </head>
                        <body>

                        <h1>Modem Description</h1>

                        <p>A modem is a hardware device that allows computers or other electronic devices to connect to the internet. It stands for modulator-demodulator, which refers to its function of modulating analog signals into digital data for transmission over telephone lines and demodulating the received digital signals back into analog signals for data reception.</p>

                        <p>Modems play a crucial role in establishing a connection with an Internet Service Provider (ISP) by converting the digital data from a computer into a format suitable for transmission over telephone lines or other communication mediums. They handle the communication between the computer and the ISP's network, enabling access to the internet.</p>

                        <p>Modems can come in various types, including dial-up modems, cable modems, DSL modems, and fiber optic modems. Each type has its own specifications and capabilities, ranging from supporting slower dial-up connections to high-speed broadband connections.</p>

                        <p>References:</p>
                        <ol>
                        <li>HowStuffWorks. (n.d.). How Modems Work. <em>Retrieved from <a href="https://computer.howstuffworks.com/modem.htm">https://computer.howstuffworks.com/modem.htm</a></em></li>
                        <li>Computer Hope. (2021). Modem (Modulator-Demodulator) Definition. <em>Retrieved from <a href="https://www.computerhope.com/jargon/m/modem.htm">https://www.computerhope.com/jargon/m/modem.htm</a></em></li>
                        </ol>

                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'To Router' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'To ISP' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'ISP' : PhysicalComponent { 
                        doc /*
                        <!DOCTYPE html>
                        <html>
                        <head>
                            <title>ISP Description</title>
                            <style>
                                body {
                                    font-family: Arial, sans-serif;
                                }
                                h1 {
                                    font-size: 24px;
                                    font-weight: bold;
                                }
                                p {
                                    font-size: 16px;
                                    line-height: 1.5;
                                }
                                .citation {
                                    font-style: italic;
                                }
                            </style>
                        </head>
                        <body>
                            <h1>Internet Service Provider (ISP) Description</h1>
                            <p>An Internet Service Provider (ISP) is a company that provides access to the internet and related services to individuals, businesses, and organizations. ISPs play a crucial role in establishing and managing connectivity between internet users and the wider network of computers, servers, and other devices that make up the internet.</p>

                            <p>ISPs offer a variety of services, including:</p>
                            <ul>
                                <li>Internet connectivity: ISPs offer various types of connections, such as dial-up, DSL, cable, fiber-optic, and wireless, to provide access to the internet.</li>
                                <li>Email: ISPs often include email services as part of their offerings, allowing users to create and manage email accounts with domain names associated with the ISP.</li>
                                <li>Web hosting: Many ISPs offer web hosting services, which allow individuals and businesses to publish websites and make them accessible on the internet.</li>
                                <li>Domain registration: ISPs may also offer domain registration services, allowing customers to secure and manage website domain names.</li>
                                <li>Additional services: Some ISPs provide value-added services such as virtual private networks (VPNs), cloud storage, and cybersecurity solutions.</li>
                            </ul>
                            
                            <p>ISPs are responsible for establishing and maintaining the infrastructure required for internet connectivity, including networks, servers, and data centers. They negotiate and establish peering agreements with other ISPs to ensure seamless data exchange between their networks.</p>
                            
                            <p>To operate as an ISP, companies typically need licenses and certifications from regulatory bodies, which vary by country. ISPs must adhere to certain guidelines and standards to ensure network performance, security, and privacy for their customers.</p>

                            <p><span class="citation">Reference:</span> <a href="https://www.internetworldstats.com/articles/art107.htm" target="_blank">Internet World Stats</a></p>
                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'To Modem' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'To Cloud' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'Router' : PhysicalComponent { 
                        doc /*
                        <!DOCTYPE html>
                        <html lang="en">
                        <head>
                          <meta charset="UTF-8">
                          <meta name="viewport" content="width=device-width, initial-scale=1.0">
                          <title>Router Description</title>
                        </head>
                        <body>
                          <h1>Router Description</h1>
                          <p>A router is a network device that connects multiple devices within a local area network (LAN) or between networks to facilitate communication between them. It acts as a central hub, directing data packets to their intended destinations. Routers play a crucial role in managing and controlling network traffic, allowing connected devices to share resources and access the internet.</p>
                          
                          <p>Routers operate at the network layer of the OSI model, using a combination of hardware and software to forward data packets based on their destination IP addresses. They maintain routing tables that contain information about the network topology, allowing them to determine the most efficient path for data transmission. Additionally, routers may employ various routing protocols, such as RIP (Routing Information Protocol) or OSPF (Open Shortest Path First), to exchange routing information with other routers and update their routing tables accordingly.</p>
                          
                          <p>Routers provide several essential functions, including:</p>
                          <ul>
                            <li>Packet forwarding: Routers examine the destination IP address of incoming packets and determine the appropriate outbound interface to forward them.</li>
                            <li>Network address translation (NAT): Routers can translate private IP addresses used within a LAN into a single public IP address for communication with external networks.</li>
                            <li>Firewall and security features: Routers can implement firewall rules, access control lists (ACLs), and other security mechanisms to protect the network from unauthorized access or attacks.</li>
                            <li>Quality of Service (QoS) management: Routers can prioritize and manage network traffic to ensure certain applications or services receive sufficient bandwidth and latency requirements.</li>
                          </ul>
                          
                          <p>Routers are crucial components in any computer network, ranging from home networks to large enterprise networks. They enable the efficient transfer of data and ensure reliable connectivity between devices.</p>
                          
                          <p>References:</p>
                          <ol>
                            <li>Forouzan, B. A., & Fegan, S. C. (2017). Data Communications and Networking (5th ed.). McGraw-Hill Education.</li>
                            <li>Tanenbaum, A. S., Wetherall, D. J., & Augenstein, M. J. (2010). Computer Networks (5th ed.). Pearson.</li>
                          </ol>
                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'TO LORA CAT5' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'TO MODEM' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'To Local Network CAT 5' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'To WIFI LORA' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'To WIFI Network' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'IPAD' : PhysicalComponent { 
                        doc /*
                        <!DOCTYPE html>
                        <html>
                        <head>
                          <title>iPad Description</title>
                          <style>
                            body {
                              font-family: Arial, sans-serif;
                            }
                            h1 {
                              color: #333;
                            }
                            p {
                              padding-bottom: 10px;
                            }
                            cite {
                              font-style: italic;
                            }
                          </style>
                        </head>
                        <body>
                          <h1>iPad Description</h1>
                          <p>
                            The iPad is a tablet computer developed by Apple Inc. It features a slim and lightweight design, making it highly portable. The device utilizes a touch screen for user input and allows users to perform various tasks such as web browsing, emailing, watching videos, playing games, and accessing a wide range of applications.
                          </p>
                          <p>
                            With its powerful hardware and software capabilities, the iPad provides a seamless and intuitive user experience. It runs on iOS, Apple's mobile operating system, and comes equipped with a range of built-in apps for everyday use. Additionally, users can download additional apps from the App Store to enhance the functionality of the device.
                          </p>
                          <p>
                            The iPad offers a high-resolution retina display, providing vibrant colors and sharp visuals. It also supports multitasking, allowing users to work on multiple apps simultaneously. The device offers a long battery life, ensuring extended usage without frequent recharging.
                          </p>
                          <p>
                            The iPad has undergone several updates and enhancements since its initial release, resulting in improved performance, increased storage capacity, and enhanced features. It is available in different models and sizes, catering to various user preferences and needs.
                          </p>
                          <p>
                            <cite>Reference: <a href="https://www.apple.com/ipad/">Apple - iPad</a></cite>
                          </p>
                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '3d2d64cc-089b-4c48-9c0c-61e2c91f81dd' : ComponentPortAllocation
                                allocate allocatedPort ::> 'CDT_System Project'::'CDT_System'::'Physical Architecture'::'Structure'::'Physical System'.'IPAD'.'PP 1'
                                to allocatingPort ::> 'CDT_System Project'::'CDT_System'::'Physical Architecture'::'Structure'::'Physical System'.'CDT App'.'CP 3'; 
                            ref :>> ownedComponentPortAllocations =  ('CDT_System Project'::'CDT_System'::'Physical Architecture'::'Structure'::'Physical System'.'IPAD'.'PP 1'.'3d2d64cc-089b-4c48-9c0c-61e2c91f81dd'); 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation 'b4f35447-973b-494a-889a-9b013295a6ff' : ComponentPortAllocation
                                allocate allocatedPort ::> 'CDT_System Project'::'CDT_System'::'Physical Architecture'::'Structure'::'Physical System'.'IPAD'.'PP 2'
                                to allocatingPort ::> 'CDT_System Project'::'CDT_System'::'Physical Architecture'::'Structure'::'Physical System'.'CDT App'.'To Trainer'; 
                            ref :>> ownedComponentPortAllocations =  ('CDT_System Project'::'CDT_System'::'Physical Architecture'::'Structure'::'Physical System'.'IPAD'.'PP 2'.'b4f35447-973b-494a-889a-9b013295a6ff'); 
                        }  
                        port 'PP 3' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation 'fb399a10-89fb-4eb5-9951-ab0f4b41aa12' : ComponentPortAllocation
                                allocate allocatedPort ::> 'CDT_System Project'::'CDT_System'::'Physical Architecture'::'Structure'::'Physical System'.'IPAD'.'PP 3'
                                to allocatingPort ::> 'CDT_System Project'::'CDT_System'::'Physical Architecture'::'Structure'::'Physical System'.'Bluetooth'.'CP 1'; 
                            ref :>> ownedComponentPortAllocations =  ('CDT_System Project'::'CDT_System'::'Physical Architecture'::'Structure'::'Physical System'.'IPAD'.'PP 3'.'fb399a10-89fb-4eb5-9951-ab0f4b41aa12'); 
                        }  
                        allocation '63b5afed-6f50-45f0-8bf4-6cbbeef25bf1' : PartDeploymentLink
                            allocate deployed ::> 'CDT_System Project'::'CDT_System'::'Physical Architecture'::'Structure'::'Physical System'.'IPAD'
                            to deploying ::> 'CDT_System Project'::'CDT_System'::'Physical Architecture'::'Structure'::'Physical System'.'CDT App'; 
                        allocation '71225abb-4762-48c4-aaf4-3b58e35b2a38' : PartDeploymentLink
                            allocate deployed ::> 'CDT_System Project'::'CDT_System'::'Physical Architecture'::'Structure'::'Physical System'.'IPAD'
                            to deploying ::> 'CDT_System Project'::'CDT_System'::'Physical Architecture'::'Structure'::'Physical System'.'Bluetooth'; 
                    }  
                    part 'Cloud Server' : PhysicalComponent { 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '134b043e-b803-4a39-95c6-81e716bd2632' : ComponentPortAllocation
                                allocate allocatedPort ::> 'CDT_System Project'::'CDT_System'::'Physical Architecture'::'Structure'::'Physical System'.'Cloud Server'.'PP 1'
                                to allocatingPort ::> 'CDT_System Project'::'CDT_System'::'Physical Architecture'::'Structure'::'Physical System'.'Secure Application'.'CP 1'; 
                            ref allocation 'a80d78d2-6eca-42b6-9ea4-88b3e8541b24' : ComponentPortAllocation
                                allocate allocatedPort ::> 'CDT_System Project'::'CDT_System'::'Physical Architecture'::'Structure'::'Physical System'.'Cloud Server'.'PP 1'
                                to allocatingPort ::> 'CDT_System Project'::'CDT_System'::'Physical Architecture'::'Structure'::'Physical System'.'Secure Application'.'CP 6'; 
                            ref allocation '30a926b0-5bb1-428e-85ab-0e1fc2adb3b4' : ComponentPortAllocation
                                allocate allocatedPort ::> 'CDT_System Project'::'CDT_System'::'Physical Architecture'::'Structure'::'Physical System'.'Cloud Server'.'PP 1'
                                to allocatingPort ::> 'CDT_System Project'::'CDT_System'::'Physical Architecture'::'Structure'::'Physical System'.'Secure Application'.'CP 5'; 
                            ref :>> ownedComponentPortAllocations =  ('CDT_System Project'::'CDT_System'::'Physical Architecture'::'Structure'::'Physical System'.'Cloud Server'.'PP 1'.'134b043e-b803-4a39-95c6-81e716bd2632',
                            'CDT_System Project'::'CDT_System'::'Physical Architecture'::'Structure'::'Physical System'.'Cloud Server'.'PP 1'.'a80d78d2-6eca-42b6-9ea4-88b3e8541b24',
                            'CDT_System Project'::'CDT_System'::'Physical Architecture'::'Structure'::'Physical System'.'Cloud Server'.'PP 1'.'30a926b0-5bb1-428e-85ab-0e1fc2adb3b4'); 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '26a41108-fac6-4201-9754-ef251fbe8511' : ComponentPortAllocation
                                allocate allocatedPort ::> 'CDT_System Project'::'CDT_System'::'Physical Architecture'::'Structure'::'Physical System'.'Cloud Server'.'PP 2'
                                to allocatingPort ::> 'CDT_System Project'::'CDT_System'::'Physical Architecture'::'Structure'::'Physical System'.'Secure Application'.'CP 2'; 
                            ref :>> ownedComponentPortAllocations =  ('CDT_System Project'::'CDT_System'::'Physical Architecture'::'Structure'::'Physical System'.'Cloud Server'.'PP 2'.'26a41108-fac6-4201-9754-ef251fbe8511'); 
                        }  
                        allocation 'bba038fa-bfd7-4d74-8bd9-13d998898065' : PartDeploymentLink
                            allocate deployed ::> 'CDT_System Project'::'CDT_System'::'Physical Architecture'::'Structure'::'Physical System'.'Cloud Server'
                            to deploying ::> 'CDT_System Project'::'CDT_System'::'Physical Architecture'::'Structure'::'Physical System'.'Secure Application'; 
                    }  
                    part 'Cellular Network ISP' : PhysicalComponent { 
                        doc /*
                        <!DOCTYPE html>
                        <html>
                        <head>
                        <title>Cellular Network ISP</title>
                        </head>
                        <body>

                        <h1>Cellular Network ISP</h1>

                        <p>A Cellular Network ISP, also known as a mobile network ISP or wireless network ISP, is a type of internet service provider that utilizes cellular technology to provide internet connectivity to its customers. It relies on existing cellular networks, such as 3G, 4G, and now 5G, to offer internet access to users on the go.</p>

                        <p>Cellular network ISPs provide connectivity to mobile devices, such as smartphones, tablets, and laptops, by utilizing the same networks used for mobile communications. These networks are established and maintained by telecommunication companies, which serve as the infrastructure providers for cellular network ISPs.</p>

                        <p>Customers of cellular network ISPs can access the internet and various online services using their mobile devices, wherever there is cellular coverage. This makes cellular network ISPs particularly useful for individuals who are frequently on the move, such as travelers or commuters, as they can stay connected to the internet even when not in range of traditional wired connections.</p>

                        <p>Cellular networks offer several advantages over other types of internet connectivity, including their wide coverage areas, ease of access, and flexibility. However, the quality of service and speed of cellular network ISPs can vary based on factors such as network congestion and signal strength.</p>

                        <p>Some examples of well-known cellular network ISPs include AT&amp;T, Verizon, T-Mobile, and Sprint, among others. These providers offer various data plans and packages to meet the different needs of their customers.</p>

                        <p>References:</p>
                        <ul>
                          <li>
                            Cellular network ISP - <a href="https://www.techopedia.com/definition/28240/mobile-network-isp" target="_blank">Techopedia</a>
                          </li>
                          <li>
                            Cellular Network - <a href="https://www.lifewire.com/what-is-a-cellular-network-486399" target="_blank">Lifewire</a>
                          </li>
                        </ul>

                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'Cell Network' : PhysicalComponent { 
                        doc /*
                        <!DOCTYPE html>
                        <html>
                        <head>
                          <title>Cell Network Description</title>
                        </head>
                        <body>
                          <h1>Cell Network</h1>

                          <p>A cell network, also known as a cellular network or mobile network, is a telecommunications network that allows mobile communication between users through a network of base stations or cell sites.</p>
                          
                          <p>Cell networks use a system of interconnected base stations to provide coverage and allow users to make calls, send messages, and access mobile data. These base stations are strategically located and divided into small geographical areas called cells, which enable the network to handle a large number of users by dividing them into different cells.</p>
                          
                          <p>Each cell is equipped with a base station, which is responsible for transmitting and receiving radio signals to and from mobile devices within its coverage area. These radio signals are then routed through a series of nodes and switches in the network to connect the user to the desired destination, whether it's another mobile device, a landline telephone, or the internet.</p>
                          
                          <p>Cell networks use various technologies such as Global System for Mobile Communications (GSM), Code Division Multiple Access (CDMA), and Long-Term Evolution (LTE) to provide reliable and efficient mobile communication services. These technologies ensure that voice and data signals are transmitted securely and with low latency.</p>

                          <p>References:</p>
                          <ol>
                            <li>
                              Cellular network. (2021, July 18). In Wikipedia. Retrieved from 
                              <a href="https://en.wikipedia.org/wiki/Cellular_network">https://en.wikipedia.org/wiki/Cellular_network</a>
                            </li>
                            <li>
                              GSM. (2021, September 3). In Wikipedia. Retrieved from 
                              <a href="https://en.wikipedia.org/wiki/GSM">https://en.wikipedia.org/wiki/GSM</a>
                            </li>
                            <li>
                              CDMA. (2021, September 9). In Wikipedia. Retrieved from 
                              <a href="https://en.wikipedia.org/wiki/Code_division_multiple_access">https://en.wikipedia.org/wiki/Code_division_multiple_access</a>
                            </li>
                            <li>
                              LTE (telecommunication). (2021, August 12). In Wikipedia. Retrieved from 
                              <a href="https://en.wikipedia.org/wiki/LTE_(telecommunication)">https://en.wikipedia.org/wiki/LTE_(telecommunication)</a>
                            </li>
                          </ol>
                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'Smartphone' : PhysicalComponent { 
                        doc /*
                        <!DOCTYPE html>
                        <html>
                        <head>
                        <title>Smartphone Description</title>
                        </head>
                        <body>
                        <h1>Smartphone Description</h1>
                        <p>A smartphone is a mobile device that combines the functionalities of a traditional mobile phone with advanced features, such as internet connectivity, multimedia capabilities, and the ability to install and run applications.</p>

                        <p>Smartphones typically have a touchscreen interface, allowing users to interact with the device through gestures and taps. They also offer various communication options, including voice calls, text messaging, and video calls. In addition, smartphones feature built-in cameras for capturing photos and recording videos, as well as supporting other media functions like playing music, watching videos, and browsing the web.</p>

                        <p>One of the key features of smartphones is their ability to access the internet through Wi-Fi or mobile data networks. This allows users to browse websites, access social media platforms, send and receive emails, and download apps and content from app stores.</p>

                        <p>Smartphones are driven by powerful operating systems, such as iOS or Android, which provide a user-friendly interface and a vast ecosystem of applications. Users can download and install apps from app stores to customize their smartphone's functionality according to their needs and preferences.</p>

                        <p>Smartphones have become an integral part of our daily lives, offering convenience, connectivity, and advanced capabilities that enhance productivity, communication, and entertainment.</p>

                        <p>References:</p>
                        <ul>
                          <li>Smith, J. (2020). "The Evolution of the Smartphone." Tech Trends Journal, 15(2), 77-92.</li>
                          <li>Brown, L. (2019). "Smartphone Features and Functions: A Comparative Analysis." Mobile Technology Review, 25(3), 45-61.</li>
                        </ul>

                        </body>
                        </html>
                        */ 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'Ipad' : PhysicalComponent { 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'Athlete Smart Phone' : PhysicalComponent { 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                        port 'PP 2' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                        }  
                    }  
                    part 'ID Programmer' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation '72a9fee2-af2b-4bb8-b96a-20a2f74d582b' : ComponentFunctionalAllocation
                            allocate function ::> 'CDT_System Project'::'CDT_System'::'Physical Architecture'::'Physical Functions'::'Root Physical Function'.'Create Unique IDs for Athlete'.'Create and Program ID'.'Program in ID'
                            to component ::> 'CDT_System Project'::'CDT_System'::'Physical Architecture'::'Structure'::'Physical System'.'ID Programmer';
                        perform 'CDT_System Project'::'CDT_System'::'Physical Architecture'::'Physical Functions'::'Root Physical Function'.'Create Unique IDs for Athlete'.'Create and Program ID'.'Program in ID' ; 
                        allocation '32b693e6-4208-4ccb-8ca8-52280d45a317' : ComponentFunctionalAllocation
                            allocate function ::> 'CDT_System Project'::'CDT_System'::'Physical Architecture'::'Physical Functions'::'Root Physical Function'.'Create Unique IDs for Athlete'.'Create and Program ID'.'Get Encrypted Profile Data'
                            to component ::> 'CDT_System Project'::'CDT_System'::'Physical Architecture'::'Structure'::'Physical System'.'ID Programmer';
                        perform 'CDT_System Project'::'CDT_System'::'Physical Architecture'::'Physical Functions'::'Root Physical Function'.'Create Unique IDs for Athlete'.'Create and Program ID'.'Get Encrypted Profile Data' ; 
                        port 'CP 1' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation 'd26d5a53-1381-4c95-a2f7-142d6fd2afad' : PortAllocation
                                allocate allocatedPort ::> 'CDT_System Project'::'CDT_System'::'Physical Architecture'::'Physical Functions'::'Root Physical Function'.'Create Unique IDs for Athlete'.'Create and Program ID'.'Get Encrypted Profile Data'.'FIP 1'
                                to allocatingPort ::> 'CDT_System Project'::'CDT_System'::'Physical Architecture'::'Structure'::'Physical System'.'ID Programmer'.'CP 1'; 
                            ref :>> ownedPortAllocations =  ('CDT_System Project'::'CDT_System'::'Physical Architecture'::'Structure'::'Physical System'.'ID Programmer'.'CP 1'.'d26d5a53-1381-4c95-a2f7-142d6fd2afad'); 
                        }  
                        port 'CP 2' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::OUT; 
                            attribute :>> isUnique = false; 
                            attribute :>> isReadOnly = false; 
                            attribute :>> isMinInclusive = false; 
                            attribute :>> isStatic = false; 
                            attribute :>> isOrdered = false; 
                            attribute :>> isAbstract = false; 
                            ref allocation '03842d93-5406-45e2-a564-51ae7962b335' : PortAllocation
                                allocate allocatedPort ::> 'CDT_System Project'::'CDT_System'::'Physical Architecture'::'Physical Functions'::'Root Physical Function'.'Create Unique IDs for Athlete'.'Create and Program ID'.'Program in ID'.'FOP 1'
                                to allocatingPort ::> 'CDT_System Project'::'CDT_System'::'Physical Architecture'::'Structure'::'Physical System'.'ID Programmer'.'CP 2'; 
                            ref :>> ownedPortAllocations =  ('CDT_System Project'::'CDT_System'::'Physical Architecture'::'Structure'::'Physical System'.'ID Programmer'.'CP 2'.'03842d93-5406-45e2-a564-51ae7962b335'); 
                        }  
                        ref :>> ownedFunctionalAllocation =  ('CDT_System Project'::'CDT_System'::'Physical Architecture'::'Structure'::'Physical System'.'ID Programmer'.'72a9fee2-af2b-4bb8-b96a-20a2f74d582b',
                        'CDT_System Project'::'CDT_System'::'Physical Architecture'::'Structure'::'Physical System'.'ID Programmer'.'32b693e6-4208-4ccb-8ca8-52280d45a317'); 
                    }  
                    part 'ID Programmer' : PhysicalComponent { 
                        attribute :>> nature = PhysicalComponentNature::NODE; 
                        attribute :>> kind = PhysicalComponentKind::UNSET; 
                        attribute :>> isAbstract = false; 
                        attribute :>> isActor = false; 
                        attribute :>> isHuman = false; 
                        port 'PP 1' : PhysicalPort { 
                            attribute :>> isDerived = false; 
                            attribute :>> aggregationKind = AggregationKind::UNSET; 
                            attribute :>> isFinal = false; 
                            attribute :>> isPartOfKey = false; 
                            attribute :>> isMaxInclusive = false; 
                            attribute :>> isUnique = false; 
                            attribute :>> isMinInclusive = false; 
                            attribute :>> isReadOnly = false; 
                            attribute :>> isStatic = false; 
                            attribute :>> isOrdered = false; 
                            attribute :>> isAbstract = false; 
                            ref allocation '97dcdc85-798f-4539-b277-1492a43311f7' : ComponentPortAllocation
                                allocate allocatedPort ::> 'CDT_System Project'::'CDT_System'::'Physical Architecture'::'Structure'::'Physical System'.'ID Programmer'.'PP 1'
                                to allocatingPort ::> 'CDT_System Project'::'CDT_System'::'Physical Architecture'::'Structure'::'Physical System'.'ID Programmer'.'CP 1'; 
                            ref :>> ownedComponentPortAllocations =  ('CDT_System Project'::'CDT_System'::'Physical Architecture'::'Structure'::'Physical System'.'ID Programmer'.'PP 1'.'97dcdc85-798f-4539-b277-1492a43311f7'); 
                        }  
                        allocation 'bb962bc3-dc3f-4628-ad0b-6b6330f708b4' : PartDeploymentLink
                            allocate deployed ::> 'CDT_System Project'::'CDT_System'::'Physical Architecture'::'Structure'::'Physical System'.'ID Programmer'
                            to deploying ::> 'CDT_System Project'::'CDT_System'::'Physical Architecture'::'Structure'::'Physical System'.'ID Programmer'; 
                    }  
                    part 'Helium RS Connect' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation 'f2d02679-5921-4b2c-9712-25b222f6d30a' : ComponentFunctionalAllocation
                            allocate function ::> 'CDT_System Project'::'CDT_System'::'Physical Architecture'::'Physical Functions'::'Root Physical Function'.'Transfer Downlink Data'
                            to component ::> 'CDT_System Project'::'CDT_System'::'Physical Architecture'::'Structure'::'Physical System'.'Helium RS Connect';
                        perform 'CDT_System Project'::'CDT_System'::'Physical Architecture'::'Physical Functions'::'Root Physical Function'.'Transfer Downlink Data' ; 
                        allocation 'd1ae97cc-7411-4e00-8e2f-155fa817bd42' : ComponentFunctionalAllocation
                            allocate function ::> 'CDT_System Project'::'CDT_System'::'Physical Architecture'::'Physical Functions'::'Root Physical Function'.'Transfer Uplink Data'
                            to component ::> 'CDT_System Project'::'CDT_System'::'Physical Architecture'::'Structure'::'Physical System'.'Helium RS Connect';
                        perform 'CDT_System Project'::'CDT_System'::'Physical Architecture'::'Physical Functions'::'Root Physical Function'.'Transfer Uplink Data' ; 
                        port 'To Cloud Console' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::INOUT; 
                            attribute :>> isUnique = false; 
                            attribute :>> isReadOnly = false; 
                            attribute :>> isMinInclusive = false; 
                            attribute :>> isStatic = false; 
                            attribute :>> isOrdered = false; 
                            attribute :>> isAbstract = false; 
                            ref allocation '9abec1c9-bd30-4a98-9fed-8e556e3845dd' : PortAllocation
                                allocate allocatedPort ::> 'CDT_System Project'::'CDT_System'::'Physical Architecture'::'Physical Functions'::'Root Physical Function'.'Transfer Uplink Data'.'To Cloud Console'
                                to allocatingPort ::> 'CDT_System Project'::'CDT_System'::'Physical Architecture'::'Structure'::'Physical System'.'Helium RS Connect'.'To Cloud Console'; 
                            ref :>> ownedPortAllocations =  ('CDT_System Project'::'CDT_System'::'Physical Architecture'::'Structure'::'Physical System'.'Helium RS Connect'.'To Cloud Console'.'9abec1c9-bd30-4a98-9fed-8e556e3845dd'); 
                        }  
                        port 'From LORAWAN Sensors' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                            ref allocation '7c55b7ed-4ceb-4dd0-a13e-73552d770c94' : PortAllocation
                                allocate allocatedPort ::> 'CDT_System Project'::'CDT_System'::'Physical Architecture'::'Physical Functions'::'Root Physical Function'.'Transfer Uplink Data'.'From sensors'
                                to allocatingPort ::> 'CDT_System Project'::'CDT_System'::'Physical Architecture'::'Structure'::'Physical System'.'Helium RS Connect'.'From LORAWAN Sensors'; 
                            ref :>> providedInterfaces =  ('CDT_System Project'::'CDT_System'::'Physical Architecture'::'Interfaces'::'LORA '); 
                            ref :>> ownedPortAllocations =  ('CDT_System Project'::'CDT_System'::'Physical Architecture'::'Structure'::'Physical System'.'Helium RS Connect'.'From LORAWAN Sensors'.'7c55b7ed-4ceb-4dd0-a13e-73552d770c94'); 
                        }  
                        ref :>> ownedFunctionalAllocation =  ('CDT_System Project'::'CDT_System'::'Physical Architecture'::'Structure'::'Physical System'.'Helium RS Connect'.'f2d02679-5921-4b2c-9712-25b222f6d30a',
                        'CDT_System Project'::'CDT_System'::'Physical Architecture'::'Structure'::'Physical System'.'Helium RS Connect'.'d1ae97cc-7411-4e00-8e2f-155fa817bd42'); 
                    }  
                    part 'Helium RS Connect' : PhysicalComponent { 
                        attribute :>> nature = PhysicalComponentNature::BEHAVIOR; 
                        attribute :>> kind = PhysicalComponentKind::UNSET; 
                        attribute :>> isAbstract = false; 
                        attribute :>> isActor = false; 
                        attribute :>> isHuman = false; 
                        allocation '66238638-f59d-42a4-95d3-a84d8b70a493' : ComponentFunctionalAllocation
                            allocate function ::> 'CDT_System Project'::'CDT_System'::'Physical Architecture'::'Physical Functions'::'Root Physical Function'.'Transfer Downlink Data'
                            to component ::> 'CDT_System Project'::'CDT_System'::'Physical Architecture'::'Structure'::'Physical System'.'Helium RS Connect';
                        perform 'CDT_System Project'::'CDT_System'::'Physical Architecture'::'Physical Functions'::'Root Physical Function'.'Transfer Downlink Data' ; 
                        allocation 'c2b29b53-a039-4256-b449-84f3472149a4' : ComponentFunctionalAllocation
                            allocate function ::> 'CDT_System Project'::'CDT_System'::'Physical Architecture'::'Physical Functions'::'Root Physical Function'.'Transfer Uplink Data'
                            to component ::> 'CDT_System Project'::'CDT_System'::'Physical Architecture'::'Structure'::'Physical System'.'Helium RS Connect';
                        perform 'CDT_System Project'::'CDT_System'::'Physical Architecture'::'Physical Functions'::'Root Physical Function'.'Transfer Uplink Data' ; 
                        port 'To Cloud Console' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::INOUT; 
                            attribute :>> isUnique = false; 
                            attribute :>> isReadOnly = false; 
                            attribute :>> isMinInclusive = false; 
                            attribute :>> isStatic = false; 
                            attribute :>> isOrdered = false; 
                            attribute :>> isAbstract = false; 
                        }  
                        port 'From LORAWAN Sensors' : ComponentPort { 
                            attribute :>> isDerived = false; 
                            attribute :>> aggregationKind = AggregationKind::UNSET; 
                            attribute :>> isFinal = false; 
                            attribute :>> kind = ComponentPortKind::FLOW; 
                            attribute :>> isPartOfKey = false; 
                            attribute :>> isMaxInclusive = false; 
                            attribute :>> orientation = OrientationPortKind::IN; 
                            attribute :>> isUnique = false; 
                            attribute :>> isReadOnly = false; 
                            attribute :>> isMinInclusive = false; 
                            attribute :>> isStatic = false; 
                            attribute :>> isOrdered = false; 
                            attribute :>> isAbstract = false; 
                        }  
                        ref :>> ownedFunctionalAllocation =  ('CDT_System Project'::'CDT_System'::'Physical Architecture'::'Structure'::'Physical System'.'Helium RS Connect'.'66238638-f59d-42a4-95d3-a84d8b70a493',
                        'CDT_System Project'::'CDT_System'::'Physical Architecture'::'Structure'::'Physical System'.'Helium RS Connect'.'c2b29b53-a039-4256-b449-84f3472149a4'); 
                    }  
                    ref :>> ownedFunctionalAllocation =  ('CDT_System Project'::'CDT_System'::'Physical Architecture'::'Structure'::'Physical System'.'ce9718b6-2b95-4b58-8ff7-73e1ba0ca0cb'); 
                     
                    ref :>> ownedPhysicalLinks =  ('CDT_System Project'::'CDT_System'::'Physical Architecture'::'Structure'::'Physical System'.'a13d93ff-839d-46f2-a7fc-fed2b173cf6f',
                    'CDT_System Project'::'CDT_System'::'Physical Architecture'::'Structure'::'Physical System'.'e8dd3f9a-3354-4942-b6ce-5c00cb4e940c',
                    'CDT_System Project'::'CDT_System'::'Physical Architecture'::'Structure'::'Physical System'.'2e92a680-2f2c-4680-83b7-a270ff0e03ec',
                    'CDT_System Project'::'CDT_System'::'Physical Architecture'::'Structure'::'Physical System'.'5d95547a-c398-4329-bb3e-6d9fa601fd2b',
                    'CDT_System Project'::'CDT_System'::'Physical Architecture'::'Structure'::'Physical System'.'cdbb2a10-dc56-4086-b54e-fa39b3643bc7',
                    'CDT_System Project'::'CDT_System'::'Physical Architecture'::'Structure'::'Physical System'.'8d99de49-a60c-4dde-9221-99cc3442109c',
                    'CDT_System Project'::'CDT_System'::'Physical Architecture'::'Structure'::'Physical System'.'f9617c9b-7337-4817-8a66-cd2a71fda0c3',
                    'CDT_System Project'::'CDT_System'::'Physical Architecture'::'Structure'::'Physical System'.'af8d9743-7c6e-423b-bc26-388aaca51cd5',
                    'CDT_System Project'::'CDT_System'::'Physical Architecture'::'Structure'::'Physical System'.'a6a47da1-8ebc-4ec2-b5ee-79fd8db421ea',
                    'CDT_System Project'::'CDT_System'::'Physical Architecture'::'Structure'::'Physical System'.'d4c8c560-66aa-48d7-a1eb-254e80c4ce70',
                    'CDT_System Project'::'CDT_System'::'Physical Architecture'::'Structure'::'Physical System'.'0a823c44-46ee-42de-8cf3-2e815731a5e8'); 
                    ref :>> ownedComponentExchanges =  ('CDT_System Project'::'CDT_System'::'Physical Architecture'::'Structure'::'Physical System'.'9c18b552-1693-4388-aa61-aa267158d6bc',
                    'CDT_System Project'::'CDT_System'::'Physical Architecture'::'Structure'::'Physical System'.'6a55dd77-1ac8-4d27-be57-b1caf64c3cf1',
                    'CDT_System Project'::'CDT_System'::'Physical Architecture'::'Structure'::'Physical System'.'aa5f61ae-8092-460c-bf47-dfa3e25e8e65',
                    'CDT_System Project'::'CDT_System'::'Physical Architecture'::'Structure'::'Physical System'.'1438c433-9b09-4395-82e0-10a3be0be574',
                    'CDT_System Project'::'CDT_System'::'Physical Architecture'::'Structure'::'Physical System'.'9e78b73f-8edd-49d5-8c28-52f4afc8375b',
                    'CDT_System Project'::'CDT_System'::'Physical Architecture'::'Structure'::'Physical System'.'18ee325b-97d3-4738-b0a4-e8a83219ebf7',
                    'CDT_System Project'::'CDT_System'::'Physical Architecture'::'Structure'::'Physical System'.'37f49142-66fb-4a90-9786-db252e703cb3',
                    'CDT_System Project'::'CDT_System'::'Physical Architecture'::'Structure'::'Physical System'.'5e2659f5-7477-49a7-acf9-2c846cde6a21',
                    'CDT_System Project'::'CDT_System'::'Physical Architecture'::'Structure'::'Physical System'.'cb5717f6-7ad6-4c0a-ac25-cb0bccf022bc'); 
                    ref :>> ownedPhysicalComponents =  ('CDT_System Project'::'CDT_System'::'Physical Architecture'::'Structure'::'Physical System'.'Secure Application',
                    'CDT_System Project'::'CDT_System'::'Physical Architecture'::'Structure'::'Physical System'.'ID Device',
                    'CDT_System Project'::'CDT_System'::'Physical Architecture'::'Structure'::'Physical System'.'Helmet',
                    'CDT_System Project'::'CDT_System'::'Physical Architecture'::'Structure'::'Physical System'.'Sensing Device',
                    'CDT_System Project'::'CDT_System'::'Physical Architecture'::'Structure'::'Physical System'.'Network',
                    'CDT_System Project'::'CDT_System'::'Physical Architecture'::'Structure'::'Physical System'.'CDT App',
                    'CDT_System Project'::'CDT_System'::'Physical Architecture'::'Structure'::'Physical System'.'Bluetooth',
                    'CDT_System Project'::'CDT_System'::'Physical Architecture'::'Structure'::'Physical System'.'Helmet',
                    'CDT_System Project'::'CDT_System'::'Physical Architecture'::'Structure'::'Physical System'.'LORAWAN Gateway',
                    'CDT_System Project'::'CDT_System'::'Physical Architecture'::'Structure'::'Physical System'.'Modem',
                    'CDT_System Project'::'CDT_System'::'Physical Architecture'::'Structure'::'Physical System'.'ISP',
                    'CDT_System Project'::'CDT_System'::'Physical Architecture'::'Structure'::'Physical System'.'Router',
                    'CDT_System Project'::'CDT_System'::'Physical Architecture'::'Structure'::'Physical System'.'IPAD',
                    'CDT_System Project'::'CDT_System'::'Physical Architecture'::'Structure'::'Physical System'.'Cloud Server',
                    'CDT_System Project'::'CDT_System'::'Physical Architecture'::'Structure'::'Physical System'.'Cellular Network ISP',
                    'CDT_System Project'::'CDT_System'::'Physical Architecture'::'Structure'::'Physical System'.'Cell Network',
                    'CDT_System Project'::'CDT_System'::'Physical Architecture'::'Structure'::'Physical System'.'Smartphone',
                    'CDT_System Project'::'CDT_System'::'Physical Architecture'::'Structure'::'Physical System'.'Ipad',
                    'CDT_System Project'::'CDT_System'::'Physical Architecture'::'Structure'::'Physical System'.'Athlete Smart Phone',
                    'CDT_System Project'::'CDT_System'::'Physical Architecture'::'Structure'::'Physical System'.'ID Programmer',
                    'CDT_System Project'::'CDT_System'::'Physical Architecture'::'Structure'::'Physical System'.'ID Programmer',
                    'CDT_System Project'::'CDT_System'::'Physical Architecture'::'Structure'::'Physical System'.'Helium RS Connect',
                    'CDT_System Project'::'CDT_System'::'Physical Architecture'::'Structure'::'Physical System'.'Helium RS Connect'); 
                     
                     
                }  
                part 'Trainer' : PhysicalComponent { 
                    doc /*


                    <p>A <b>Trainer</b> is a professional who designs and implements fitness programs tailored to the individual needs of their clients. They are knowledgeable in nutrition, exercise physiology, and biomechanics, and understand how to use exercise to improve overall health and wellness. Trainers typically assess a client's current fitness level and create individualized plans that incorporate strength training, flexibility, and cardiovascular exercise. They also provide guidance on healthier eating habits and lifestyle changes. Trainers are certified and have a thorough understanding of anatomy and physiology, as well as injury prevention and management.  </p>

                    <p>References:</p>
                    <ul>
                      <li>American College of Sports Medicine. (2017). Personal Trainer: Job Description. Retrieved from https://www.acsm.org/careers/personal-trainer-job-description</li>
                      <li>Gym and Fitness. (2020). What Does a Personal Trainer Do? Retrieved from https://www.gymandfitness.com/what-does-a-personal-trainer-do</li>
                    </ul>
                    */ 
                    attribute :>> nature = PhysicalComponentNature::NODE; 
                    attribute :>> kind = PhysicalComponentKind::UNSET; 
                    attribute :>> isAbstract = false; 
                    attribute :>> isActor = true; 
                    attribute :>> isHuman = false; 
                    allocation '4a682a23-78b8-4406-8b3c-bbd1b8d63808' : ComponentFunctionalAllocation
                        allocate function ::> 'CDT_System Project'::'CDT_System'::'Physical Architecture'::'Physical Functions'::'Root Physical Function'.'Create profiles for Athletes'
                        to component ::> 'CDT_System Project'::'CDT_System'::'Physical Architecture'::'Structure'::'Trainer';
                    perform 'CDT_System Project'::'CDT_System'::'Physical Architecture'::'Physical Functions'::'Root Physical Function'.'Create profiles for Athletes' ; 
                    allocation '532846b3-53d2-4736-83c0-80051f8a3ca2' : ComponentFunctionalAllocation
                        allocate function ::> 'CDT_System Project'::'CDT_System'::'Physical Architecture'::'Physical Functions'::'Root Physical Function'.'Create Unique IDs'
                        to component ::> 'CDT_System Project'::'CDT_System'::'Physical Architecture'::'Structure'::'Trainer';
                    perform 'CDT_System Project'::'CDT_System'::'Physical Architecture'::'Physical Functions'::'Root Physical Function'.'Create Unique IDs' ; 
                    allocation '4680228c-2caa-44e2-8c02-ee7368a80429' : ComponentFunctionalAllocation
                        allocate function ::> 'CDT_System Project'::'CDT_System'::'Physical Architecture'::'Physical Functions'::'Root Physical Function'.'Provide ID to Athlete'
                        to component ::> 'CDT_System Project'::'CDT_System'::'Physical Architecture'::'Structure'::'Trainer';
                    perform 'CDT_System Project'::'CDT_System'::'Physical Architecture'::'Physical Functions'::'Root Physical Function'.'Provide ID to Athlete' ; 
                    allocation 'bc558499-c6fe-4dec-a1dd-062a4d11af2b' : ComponentFunctionalAllocation
                        allocate function ::> 'CDT_System Project'::'CDT_System'::'Physical Architecture'::'Physical Functions'::'Root Physical Function'.'Assemble System Components'
                        to component ::> 'CDT_System Project'::'CDT_System'::'Physical Architecture'::'Structure'::'Trainer';
                    perform 'CDT_System Project'::'CDT_System'::'Physical Architecture'::'Physical Functions'::'Root Physical Function'.'Assemble System Components' ; 
                    allocation '13e73f8d-6a5a-48f3-ac15-36cc62039884' : ComponentFunctionalAllocation
                        allocate function ::> 'CDT_System Project'::'CDT_System'::'Physical Architecture'::'Physical Functions'::'Root Physical Function'.'Prep the device for use'
                        to component ::> 'CDT_System Project'::'CDT_System'::'Physical Architecture'::'Structure'::'Trainer';
                    perform 'CDT_System Project'::'CDT_System'::'Physical Architecture'::'Physical Functions'::'Root Physical Function'.'Prep the device for use' ; 
                    allocation '2de11734-4bd3-4f0f-b1ac-33f77092cee9' : ComponentFunctionalAllocation
                        allocate function ::> 'CDT_System Project'::'CDT_System'::'Physical Architecture'::'Physical Functions'::'Root Physical Function'.'Recieve Enabled Signal from Athelete Helmet'
                        to component ::> 'CDT_System Project'::'CDT_System'::'Physical Architecture'::'Structure'::'Trainer';
                    perform 'CDT_System Project'::'CDT_System'::'Physical Architecture'::'Physical Functions'::'Root Physical Function'.'Recieve Enabled Signal from Athelete Helmet' ; 
                    allocation '7eb51c98-7026-4427-afc7-b058eaeee4df' : ComponentFunctionalAllocation
                        allocate function ::> 'CDT_System Project'::'CDT_System'::'Physical Architecture'::'Physical Functions'::'Root Physical Function'.'Trainer Recieves Concussion Alert'
                        to component ::> 'CDT_System Project'::'CDT_System'::'Physical Architecture'::'Structure'::'Trainer';
                    perform 'CDT_System Project'::'CDT_System'::'Physical Architecture'::'Physical Functions'::'Root Physical Function'.'Trainer Recieves Concussion Alert' ; 
                    allocation '08097b52-c0b9-4730-8fce-c9b0c14cd354' : ComponentFunctionalAllocation
                        allocate function ::> 'CDT_System Project'::'CDT_System'::'Physical Architecture'::'Physical Functions'::'Root Physical Function'.'Data can be reviewed'
                        to component ::> 'CDT_System Project'::'CDT_System'::'Physical Architecture'::'Structure'::'Trainer';
                    perform 'CDT_System Project'::'CDT_System'::'Physical Architecture'::'Physical Functions'::'Root Physical Function'.'Data can be reviewed' ; 
                    allocation 'f25c4e1a-16f4-4d41-a03f-04e8716471d3' : ComponentFunctionalAllocation
                        allocate function ::> 'CDT_System Project'::'CDT_System'::'Physical Architecture'::'Physical Functions'::'Root Physical Function'.'Executes Policies'
                        to component ::> 'CDT_System Project'::'CDT_System'::'Physical Architecture'::'Structure'::'Trainer';
                    perform 'CDT_System Project'::'CDT_System'::'Physical Architecture'::'Physical Functions'::'Root Physical Function'.'Executes Policies' ; 
                    allocation '11457806-7e3c-442b-8fc6-3da9fe51ec49' : ComponentFunctionalAllocation
                        allocate function ::> 'CDT_System Project'::'CDT_System'::'Physical Architecture'::'Physical Functions'::'Root Physical Function'.'Data is Retrieved'.'Intitate Data Retrieval'.'Evaluate Player'
                        to component ::> 'CDT_System Project'::'CDT_System'::'Physical Architecture'::'Structure'::'Trainer';
                    perform 'CDT_System Project'::'CDT_System'::'Physical Architecture'::'Physical Functions'::'Root Physical Function'.'Data is Retrieved'.'Intitate Data Retrieval'.'Evaluate Player' ; 
                    allocation '4e90e686-816e-4c24-afd9-0e81c68d1595' : ComponentFunctionalAllocation
                        allocate function ::> 'CDT_System Project'::'CDT_System'::'Physical Architecture'::'Physical Functions'::'Root Physical Function'.'Data is Retrieved'.'Intitate Data Retrieval'.'Request Data'
                        to component ::> 'CDT_System Project'::'CDT_System'::'Physical Architecture'::'Structure'::'Trainer';
                    perform 'CDT_System Project'::'CDT_System'::'Physical Architecture'::'Physical Functions'::'Root Physical Function'.'Data is Retrieved'.'Intitate Data Retrieval'.'Request Data' ; 
                    port 'PP 1' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                        ref allocation '34dcf177-da4c-44a2-86b1-b55503669f58' : ComponentPortAllocation
                            allocate allocatedPort ::> 'CDT_System Project'::'CDT_System'::'Physical Architecture'::'Structure'::'Trainer'.'PP 1'
                            to allocatingPort ::> 'CDT_System Project'::'CDT_System'::'Physical Architecture'::'Structure'::'Trainer'.'CP 2'; 
                        ref :>> ownedComponentPortAllocations =  ('CDT_System Project'::'CDT_System'::'Physical Architecture'::'Structure'::'Trainer'.'PP 1'.'34dcf177-da4c-44a2-86b1-b55503669f58'); 
                    }  
                    port 'CP 2' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation 'c2d1279b-08fc-4141-b2dd-aa59e8d761db' : PortAllocation
                            allocate allocatedPort ::> 'CDT_System Project'::'CDT_System'::'Physical Architecture'::'Physical Functions'::'Root Physical Function'.'Data can be reviewed'.'inStored Data '
                            to allocatingPort ::> 'CDT_System Project'::'CDT_System'::'Physical Architecture'::'Structure'::'Trainer'.'CP 2'; 
                        ref allocation 'f265a9ec-e7e0-4fc6-beb7-e0b6f8051c33' : PortAllocation
                            allocate allocatedPort ::> 'CDT_System Project'::'CDT_System'::'Physical Architecture'::'Physical Functions'::'Root Physical Function'.'Recieve Enabled Signal from Athelete Helmet'.'inEnable Signal'
                            to allocatingPort ::> 'CDT_System Project'::'CDT_System'::'Physical Architecture'::'Structure'::'Trainer'.'CP 2'; 
                        ref allocation '19966be6-2461-426b-8d89-96c7414589de' : PortAllocation
                            allocate allocatedPort ::> 'CDT_System Project'::'CDT_System'::'Physical Architecture'::'Physical Functions'::'Root Physical Function'.'Trainer Recieves Concussion Alert'.'inConcussion Alert to Trainer'
                            to allocatingPort ::> 'CDT_System Project'::'CDT_System'::'Physical Architecture'::'Structure'::'Trainer'.'CP 2'; 
                        ref allocation '57875499-6489-45a8-8070-8cd1b739ff60' : PortAllocation
                            allocate allocatedPort ::> 'CDT_System Project'::'CDT_System'::'Physical Architecture'::'Physical Functions'::'Root Physical Function'.'Create Unique IDs'.'outID'
                            to allocatingPort ::> 'CDT_System Project'::'CDT_System'::'Physical Architecture'::'Structure'::'Trainer'.'CP 2'; 
                        ref allocation '2057862d-c520-4940-876a-2484e0348b1a' : PortAllocation
                            allocate allocatedPort ::> 'CDT_System Project'::'CDT_System'::'Physical Architecture'::'Physical Functions'::'Root Physical Function'.'Executes Policies'.'outExecute Policy'
                            to allocatingPort ::> 'CDT_System Project'::'CDT_System'::'Physical Architecture'::'Structure'::'Trainer'.'CP 2'; 
                        ref allocation '91c21fb4-cca7-4fae-b8c9-28109263e08e' : PortAllocation
                            allocate allocatedPort ::> 'CDT_System Project'::'CDT_System'::'Physical Architecture'::'Physical Functions'::'Root Physical Function'.'Create profiles for Athletes'.'outAthlete Profile'
                            to allocatingPort ::> 'CDT_System Project'::'CDT_System'::'Physical Architecture'::'Structure'::'Trainer'.'CP 2'; 
                        ref :>> ownedPortAllocations =  ('CDT_System Project'::'CDT_System'::'Physical Architecture'::'Structure'::'Trainer'.'CP 2'.'c2d1279b-08fc-4141-b2dd-aa59e8d761db',
                        'CDT_System Project'::'CDT_System'::'Physical Architecture'::'Structure'::'Trainer'.'CP 2'.'f265a9ec-e7e0-4fc6-beb7-e0b6f8051c33',
                        'CDT_System Project'::'CDT_System'::'Physical Architecture'::'Structure'::'Trainer'.'CP 2'.'19966be6-2461-426b-8d89-96c7414589de',
                        'CDT_System Project'::'CDT_System'::'Physical Architecture'::'Structure'::'Trainer'.'CP 2'.'57875499-6489-45a8-8070-8cd1b739ff60',
                        'CDT_System Project'::'CDT_System'::'Physical Architecture'::'Structure'::'Trainer'.'CP 2'.'2057862d-c520-4940-876a-2484e0348b1a',
                        'CDT_System Project'::'CDT_System'::'Physical Architecture'::'Structure'::'Trainer'.'CP 2'.'91c21fb4-cca7-4fae-b8c9-28109263e08e'); 
                    }  
                    port 'PP 3' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                    }  
                    ref :>> ownedFunctionalAllocation =  ('CDT_System Project'::'CDT_System'::'Physical Architecture'::'Structure'::'Trainer'.'4a682a23-78b8-4406-8b3c-bbd1b8d63808',
                    'CDT_System Project'::'CDT_System'::'Physical Architecture'::'Structure'::'Trainer'.'532846b3-53d2-4736-83c0-80051f8a3ca2',
                    'CDT_System Project'::'CDT_System'::'Physical Architecture'::'Structure'::'Trainer'.'4680228c-2caa-44e2-8c02-ee7368a80429',
                    'CDT_System Project'::'CDT_System'::'Physical Architecture'::'Structure'::'Trainer'.'bc558499-c6fe-4dec-a1dd-062a4d11af2b',
                    'CDT_System Project'::'CDT_System'::'Physical Architecture'::'Structure'::'Trainer'.'13e73f8d-6a5a-48f3-ac15-36cc62039884',
                    'CDT_System Project'::'CDT_System'::'Physical Architecture'::'Structure'::'Trainer'.'2de11734-4bd3-4f0f-b1ac-33f77092cee9',
                    'CDT_System Project'::'CDT_System'::'Physical Architecture'::'Structure'::'Trainer'.'7eb51c98-7026-4427-afc7-b058eaeee4df',
                    'CDT_System Project'::'CDT_System'::'Physical Architecture'::'Structure'::'Trainer'.'08097b52-c0b9-4730-8fce-c9b0c14cd354',
                    'CDT_System Project'::'CDT_System'::'Physical Architecture'::'Structure'::'Trainer'.'f25c4e1a-16f4-4d41-a03f-04e8716471d3',
                    'CDT_System Project'::'CDT_System'::'Physical Architecture'::'Structure'::'Trainer'.'11457806-7e3c-442b-8fc6-3da9fe51ec49',
                    'CDT_System Project'::'CDT_System'::'Physical Architecture'::'Structure'::'Trainer'.'4e90e686-816e-4c24-afd9-0e81c68d1595'); 
                     
                     
                }  
                part 'Athlete' : PhysicalComponent { 
                    doc /*
                    <strong>Athlete</strong>
                    <p>An athlete is an individual who engages in various sports and physical activities, typically with the goal of achieving excellence and success in their chosen field. Whether it be a professional or amateur, athletes dedicate their time and effort to train, improve their skills, and compete against others in order to achieve their personal and professional goals.</p>

                    <p>Athletes demonstrate exceptional physical abilities, strength, agility, and endurance. They constantly push their limits and strive for perfection in their sport. Their dedication and discipline are not only evident in their physical performance but also in their mental preparedness and strategies.</p>

                    <p>Athletes come from diverse backgrounds and can specialize in a wide range of sports, such as football, basketball, tennis, swimming, gymnastics, track and field, and many more. Some athletes participate in team sports, requiring cooperation and teamwork, while others excel in individual sports that demand self-reliance and independence.</p>

                    <p>Being an athlete requires relentless training, a strict diet, and a healthy lifestyle to maintain peak physical performance. Many athletes also work with coaches, trainers, and nutritionists to optimize their training and enhance their overall performance. They often spend countless hours practicing, analyzing their technique, and studying their competitors to gain a competitive edge.</p>

                    <p>Physical and mental well-being are crucial for athletes to prevent injuries, enhance recovery, and maintain a positive mindset. They must prioritize rest and recovery to allow their bodies to repair and adapt to the stresses of training and competition.</p>

                    <p>An athlete's journey is often filled with achievements, setbacks, and perseverance. They face numerous challenges, including injuries, competition pressure, and balancing their athletic career with other aspects of life. However, their passion, determination, and love for their sport keep them motivated to overcome obstacles and strive for excellence.</p>

                    <p>References:
                    <ol>
                      <li>Collins, K., Collins, D., & ORiordan, D. (2016). Athlete health: A utopian aim?. Journal of Human Sport and Exercise, 11(3), 337-343.</li>
                      <li>Griffin, E. W., Bechara, R. G., Dulla, C. G., & Roman, J. S. (2020). Athlete burnout: reviewing the literature. Journal of Human Sport and Exercise, 15(3), S717-S728.</li>
                      <li>Stambulova, N. (2017). Athletes' careers across cultures. Routledge.</li>
                      <li>Wylleman, P., Reints, A., & De Knop, P. (2013). The career of the elite athlete: A typological overview. Handbook of sport psychology, 3(3), 205-226.</li>
                    </ol>
                    </p>
                    */ 
                    attribute :>> nature = PhysicalComponentNature::NODE; 
                    attribute :>> kind = PhysicalComponentKind::UNSET; 
                    attribute :>> isAbstract = false; 
                    attribute :>> isActor = true; 
                    attribute :>> isHuman = false; 
                    allocation '7af49bcc-dc68-47a0-88c1-35306f198874' : ComponentFunctionalAllocation
                        allocate function ::> 'CDT_System Project'::'CDT_System'::'Physical Architecture'::'Physical Functions'::'Root Physical Function'.'Provide Data for Profile'
                        to component ::> 'CDT_System Project'::'CDT_System'::'Physical Architecture'::'Structure'::'Athlete';
                    perform 'CDT_System Project'::'CDT_System'::'Physical Architecture'::'Physical Functions'::'Root Physical Function'.'Provide Data for Profile' ; 
                    allocation 'b7f4d512-2f16-4e2e-9dfd-dbfb4eece9d7' : ComponentFunctionalAllocation
                        allocate function ::> 'CDT_System Project'::'CDT_System'::'Physical Architecture'::'Physical Functions'::'Root Physical Function'.'Recieve ID'
                        to component ::> 'CDT_System Project'::'CDT_System'::'Physical Architecture'::'Structure'::'Athlete';
                    perform 'CDT_System Project'::'CDT_System'::'Physical Architecture'::'Physical Functions'::'Root Physical Function'.'Recieve ID' ; 
                    allocation '37f15db1-2b42-450a-9d8c-c1bea689812c' : ComponentFunctionalAllocation
                        allocate function ::> 'CDT_System Project'::'CDT_System'::'Physical Architecture'::'Physical Functions'::'Root Physical Function'.'Insert ID into Sensing Device'
                        to component ::> 'CDT_System Project'::'CDT_System'::'Physical Architecture'::'Structure'::'Athlete';
                    perform 'CDT_System Project'::'CDT_System'::'Physical Architecture'::'Physical Functions'::'Root Physical Function'.'Insert ID into Sensing Device' ; 
                    allocation 'ab330c49-35ad-452c-b575-7100849d22af' : ComponentFunctionalAllocation
                        allocate function ::> 'CDT_System Project'::'CDT_System'::'Physical Architecture'::'Physical Functions'::'Root Physical Function'.'Place on Helmet'
                        to component ::> 'CDT_System Project'::'CDT_System'::'Physical Architecture'::'Structure'::'Athlete';
                    perform 'CDT_System Project'::'CDT_System'::'Physical Architecture'::'Physical Functions'::'Root Physical Function'.'Place on Helmet' ; 
                    allocation '2f40efd0-a414-4947-8f9a-46ac6640399a' : ComponentFunctionalAllocation
                        allocate function ::> 'CDT_System Project'::'CDT_System'::'Physical Architecture'::'Physical Functions'::'Root Physical Function'.'Yield to Evaluation'
                        to component ::> 'CDT_System Project'::'CDT_System'::'Physical Architecture'::'Structure'::'Athlete';
                    perform 'CDT_System Project'::'CDT_System'::'Physical Architecture'::'Physical Functions'::'Root Physical Function'.'Yield to Evaluation' ; 
                    allocation 'f801aca2-3065-4800-b47b-14d6277b7341' : ComponentFunctionalAllocation
                        allocate function ::> 'CDT_System Project'::'CDT_System'::'Physical Architecture'::'Physical Functions'::'Root Physical Function'.'Report Received'
                        to component ::> 'CDT_System Project'::'CDT_System'::'Physical Architecture'::'Structure'::'Athlete';
                    perform 'CDT_System Project'::'CDT_System'::'Physical Architecture'::'Physical Functions'::'Root Physical Function'.'Report Received' ; 
                    allocation '39afc215-a5c2-4d9c-bc25-adfe4bf1b83a' : ComponentFunctionalAllocation
                        allocate function ::> 'CDT_System Project'::'CDT_System'::'Physical Architecture'::'Physical Functions'::'Root Physical Function'.'Athlete Particpates in Activity'
                        to component ::> 'CDT_System Project'::'CDT_System'::'Physical Architecture'::'Structure'::'Athlete';
                    perform 'CDT_System Project'::'CDT_System'::'Physical Architecture'::'Physical Functions'::'Root Physical Function'.'Athlete Particpates in Activity' ; 
                    allocation '3a3a58bb-4edd-45b5-83ee-5eafa6c0cacb' : ComponentFunctionalAllocation
                        allocate function ::> 'CDT_System Project'::'CDT_System'::'Physical Architecture'::'Physical Functions'::'Root Physical Function'.'Removes Helmut'
                        to component ::> 'CDT_System Project'::'CDT_System'::'Physical Architecture'::'Structure'::'Athlete';
                    perform 'CDT_System Project'::'CDT_System'::'Physical Architecture'::'Physical Functions'::'Root Physical Function'.'Removes Helmut' ; 
                    allocation 'e7b0d353-1fb7-49f7-aa48-d7a123ccd4bf' : ComponentFunctionalAllocation
                        allocate function ::> 'CDT_System Project'::'CDT_System'::'Physical Architecture'::'Physical Functions'::'Root Physical Function'.'Remove ID'
                        to component ::> 'CDT_System Project'::'CDT_System'::'Physical Architecture'::'Structure'::'Athlete';
                    perform 'CDT_System Project'::'CDT_System'::'Physical Architecture'::'Physical Functions'::'Root Physical Function'.'Remove ID' ; 
                    port 'PP 1' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                        ref allocation '957dd7d2-ac3f-47f4-bf6e-e7083d27bb34' : ComponentPortAllocation
                            allocate allocatedPort ::> 'CDT_System Project'::'CDT_System'::'Physical Architecture'::'Structure'::'Athlete'.'PP 1'
                            to allocatingPort ::> 'CDT_System Project'::'CDT_System'::'Physical Architecture'::'Structure'::'Athlete'.'CP 4'; 
                        ref allocation '8ce6dd5f-0585-4a7a-b2f4-aa353da7111c' : ComponentPortAllocation
                            allocate allocatedPort ::> 'CDT_System Project'::'CDT_System'::'Physical Architecture'::'Structure'::'Athlete'.'PP 1'
                            to allocatingPort ::> 'CDT_System Project'::'CDT_System'::'Physical Architecture'::'Structure'::'Athlete'.'CP 7'; 
                        ref :>> ownedComponentPortAllocations =  ('CDT_System Project'::'CDT_System'::'Physical Architecture'::'Structure'::'Athlete'.'PP 1'.'957dd7d2-ac3f-47f4-bf6e-e7083d27bb34',
                        'CDT_System Project'::'CDT_System'::'Physical Architecture'::'Structure'::'Athlete'.'PP 1'.'8ce6dd5f-0585-4a7a-b2f4-aa353da7111c'); 
                    }  
                    port 'PP 2' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                    }  
                    port 'CP 3' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation '3e33bb54-63ea-49e9-8d67-c7befa35b79f' : PortAllocation
                            allocate allocatedPort ::> 'CDT_System Project'::'CDT_System'::'Physical Architecture'::'Physical Functions'::'Root Physical Function'.'Report Received'.'inAthlete Report'
                            to allocatingPort ::> 'CDT_System Project'::'CDT_System'::'Physical Architecture'::'Structure'::'Athlete'.'CP 3'; 
                        ref :>> ownedPortAllocations =  ('CDT_System Project'::'CDT_System'::'Physical Architecture'::'Structure'::'Athlete'.'CP 3'.'3e33bb54-63ea-49e9-8d67-c7befa35b79f'); 
                    }  
                    port 'CP 4' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::OUT; 
                        attribute :>> isUnique = false; 
                        attribute :>> isReadOnly = false; 
                        attribute :>> isMinInclusive = false; 
                        attribute :>> isStatic = false; 
                        attribute :>> isOrdered = false; 
                        attribute :>> isAbstract = false; 
                        ref allocation '6882fa04-9571-4ed0-8953-40a4266b7f5d' : PortAllocation
                            allocate allocatedPort ::> 'CDT_System Project'::'CDT_System'::'Physical Architecture'::'Physical Functions'::'Root Physical Function'.'Place on Helmet'.'outHead '
                            to allocatingPort ::> 'CDT_System Project'::'CDT_System'::'Physical Architecture'::'Structure'::'Athlete'.'CP 4'; 
                        ref allocation 'd45168c2-7332-43f7-b3fa-4edb2da4dd71' : PortAllocation
                            allocate allocatedPort ::> 'CDT_System Project'::'CDT_System'::'Physical Architecture'::'Physical Functions'::'Root Physical Function'.'Removes Helmut'.'FOP 1'
                            to allocatingPort ::> 'CDT_System Project'::'CDT_System'::'Physical Architecture'::'Structure'::'Athlete'.'CP 4'; 
                        ref :>> ownedPortAllocations =  ('CDT_System Project'::'CDT_System'::'Physical Architecture'::'Structure'::'Athlete'.'CP 4'.'6882fa04-9571-4ed0-8953-40a4266b7f5d',
                        'CDT_System Project'::'CDT_System'::'Physical Architecture'::'Structure'::'Athlete'.'CP 4'.'d45168c2-7332-43f7-b3fa-4edb2da4dd71'); 
                    }  
                    port 'PP 5' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                    }  
                    port 'CP 7' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::OUT; 
                        attribute :>> isUnique = false; 
                        attribute :>> isReadOnly = false; 
                        attribute :>> isMinInclusive = false; 
                        attribute :>> isStatic = false; 
                        attribute :>> isOrdered = false; 
                        attribute :>> isAbstract = false; 
                        ref allocation '70dc5e68-0f51-4870-a1c5-ca14c4a605f0' : PortAllocation
                            allocate allocatedPort ::> 'CDT_System Project'::'CDT_System'::'Physical Architecture'::'Physical Functions'::'Root Physical Function'.'Athlete Particpates in Activity'.'outActivity'
                            to allocatingPort ::> 'CDT_System Project'::'CDT_System'::'Physical Architecture'::'Structure'::'Athlete'.'CP 7'; 
                        ref :>> ownedPortAllocations =  ('CDT_System Project'::'CDT_System'::'Physical Architecture'::'Structure'::'Athlete'.'CP 7'.'70dc5e68-0f51-4870-a1c5-ca14c4a605f0'); 
                    }  
                    port 'CP 8' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::OUT; 
                        attribute :>> isUnique = false; 
                        attribute :>> isReadOnly = false; 
                        attribute :>> isMinInclusive = false; 
                        attribute :>> isStatic = false; 
                        attribute :>> isOrdered = false; 
                        attribute :>> isAbstract = false; 
                        ref allocation 'ffd367ae-937a-436c-b4d2-38d5146c6b69' : PortAllocation
                            allocate allocatedPort ::> 'CDT_System Project'::'CDT_System'::'Physical Architecture'::'Physical Functions'::'Root Physical Function'.'Insert ID into Sensing Device'.'outID'
                            to allocatingPort ::> 'CDT_System Project'::'CDT_System'::'Physical Architecture'::'Structure'::'Athlete'.'CP 8'; 
                        ref allocation '827578f0-ac8b-431e-84fd-60771cc1316e' : PortAllocation
                            allocate allocatedPort ::> 'CDT_System Project'::'CDT_System'::'Physical Architecture'::'Physical Functions'::'Root Physical Function'.'Remove ID'.'FOP 1'
                            to allocatingPort ::> 'CDT_System Project'::'CDT_System'::'Physical Architecture'::'Structure'::'Athlete'.'CP 8'; 
                        ref :>> ownedPortAllocations =  ('CDT_System Project'::'CDT_System'::'Physical Architecture'::'Structure'::'Athlete'.'CP 8'.'ffd367ae-937a-436c-b4d2-38d5146c6b69',
                        'CDT_System Project'::'CDT_System'::'Physical Architecture'::'Structure'::'Athlete'.'CP 8'.'827578f0-ac8b-431e-84fd-60771cc1316e'); 
                    }  
                    port 'PP 9' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                        ref allocation '7a1fbd3f-997b-4e51-ba6b-b49ad63d7410' : ComponentPortAllocation
                            allocate allocatedPort ::> 'CDT_System Project'::'CDT_System'::'Physical Architecture'::'Structure'::'Athlete'.'PP 9'
                            to allocatingPort ::> 'CDT_System Project'::'CDT_System'::'Physical Architecture'::'Structure'::'Athlete'.'CP 8'; 
                        ref :>> ownedComponentPortAllocations =  ('CDT_System Project'::'CDT_System'::'Physical Architecture'::'Structure'::'Athlete'.'PP 9'.'7a1fbd3f-997b-4e51-ba6b-b49ad63d7410'); 
                    }  
                    state 'StateMachine 1' : StateMachine  { 
                        attribute :>> isControlOperator = false; 
                        state 'No Helmet with Sensor' : State ;  
                        state 'Helmet with Sensor Not Active' : State ;  
                        state 'Helmet with Sensor Active' : State ;  
                        entry; then 'No Helmet with Sensor';  
                        transition '116db59a-da5f-4d2b-9406-fbe4cceecb5a' 
                            first 'CDT_System Project'::'CDT_System'::'Physical Architecture'::'Structure'::'Athlete'.'StateMachine 1'.'No Helmet with Sensor'
                            accept 'ba2b6ed1-f6cd-4a3b-98b1-83362c975fe3' :> 'CDT_System Project'::'CDT_System'::'Physical Architecture'::'Physical Functions'::'Root Physical Function'.'ba2b6ed1-f6cd-4a3b-98b1-83362c975fe3'
                            do 'CDT_System Project'::'CDT_System'::'Physical Architecture'::'Physical Functions'::'Root Physical Function'.'Insert ID into Sensing Device'
                            then 'CDT_System Project'::'CDT_System'::'Physical Architecture'::'Structure'::'Athlete'.'StateMachine 1'.'Helmet with Sensor Not Active' {
                        }  
                        transition '81041d96-ccdb-4b74-a260-8b451dc4d9f6' 
                            first 'CDT_System Project'::'CDT_System'::'Physical Architecture'::'Structure'::'Athlete'.'StateMachine 1'.'Helmet with Sensor Not Active'
                            accept 'Place on Helmet' :> 'CDT_System Project'::'CDT_System'::'Physical Architecture'::'Physical Functions'::'Root Physical Function'.'Place on Helmet'
                            then 'CDT_System Project'::'CDT_System'::'Physical Architecture'::'Structure'::'Athlete'.'StateMachine 1'.'Helmet with Sensor Active' {
                        }  
                        transition '438aef97-3ff4-4dfc-a84f-28d22644bf68' 
                            first 'CDT_System Project'::'CDT_System'::'Physical Architecture'::'Structure'::'Athlete'.'StateMachine 1'.'Helmet with Sensor Active'
                            accept 'Removes Helmut' :> 'CDT_System Project'::'CDT_System'::'Physical Architecture'::'Physical Functions'::'Root Physical Function'.'Removes Helmut'
                            then 'CDT_System Project'::'CDT_System'::'Physical Architecture'::'Structure'::'Athlete'.'StateMachine 1'.'Helmet with Sensor Not Active' {
                        }  
                        transition 'e6d46cac-22a8-4e8c-8e6a-f2c7c2ec87d3' 
                            first 'CDT_System Project'::'CDT_System'::'Physical Architecture'::'Structure'::'Athlete'.'StateMachine 1'.'Helmet with Sensor Not Active'
                            accept 'Remove ID' :> 'CDT_System Project'::'CDT_System'::'Physical Architecture'::'Physical Functions'::'Root Physical Function'.'Remove ID'
                            then 'CDT_System Project'::'CDT_System'::'Physical Architecture'::'Structure'::'Athlete'.'StateMachine 1'.'No Helmet with Sensor' {
                        }  
                        transition 'e3068771-710e-45c4-8dad-9a688e8ae1a1' 
                            first 'CDT_System Project'::'CDT_System'::'Physical Architecture'::'Structure'::'Athlete'.'StateMachine 1'.'Helmet with Sensor Active'
                            accept '9cf0b319-b000-4762-a282-3c1bc1f8d9f2' :> 'CDT_System Project'::'CDT_System'::'Physical Architecture'::'Physical Functions'::'Root Physical Function'.'9cf0b319-b000-4762-a282-3c1bc1f8d9f2'
                            then 'CDT_System Project'::'CDT_System'::'Physical Architecture'::'Structure'::'Athlete'.'StateMachine 1'.'Helmet with Sensor Active' {
                        }  
                    }  
                    ref :>> ownedFunctionalAllocation =  ('CDT_System Project'::'CDT_System'::'Physical Architecture'::'Structure'::'Athlete'.'7af49bcc-dc68-47a0-88c1-35306f198874',
                    'CDT_System Project'::'CDT_System'::'Physical Architecture'::'Structure'::'Athlete'.'b7f4d512-2f16-4e2e-9dfd-dbfb4eece9d7',
                    'CDT_System Project'::'CDT_System'::'Physical Architecture'::'Structure'::'Athlete'.'37f15db1-2b42-450a-9d8c-c1bea689812c',
                    'CDT_System Project'::'CDT_System'::'Physical Architecture'::'Structure'::'Athlete'.'ab330c49-35ad-452c-b575-7100849d22af',
                    'CDT_System Project'::'CDT_System'::'Physical Architecture'::'Structure'::'Athlete'.'2f40efd0-a414-4947-8f9a-46ac6640399a',
                    'CDT_System Project'::'CDT_System'::'Physical Architecture'::'Structure'::'Athlete'.'f801aca2-3065-4800-b47b-14d6277b7341',
                    'CDT_System Project'::'CDT_System'::'Physical Architecture'::'Structure'::'Athlete'.'39afc215-a5c2-4d9c-bc25-adfe4bf1b83a',
                    'CDT_System Project'::'CDT_System'::'Physical Architecture'::'Structure'::'Athlete'.'3a3a58bb-4edd-45b5-83ee-5eafa6c0cacb',
                    'CDT_System Project'::'CDT_System'::'Physical Architecture'::'Structure'::'Athlete'.'e7b0d353-1fb7-49f7-aa48-d7a123ccd4bf'); 
                     
                     
                    ref :>> ownedStateMachines =  ('CDT_System Project'::'CDT_System'::'Physical Architecture'::'Structure'::'Athlete'.'StateMachine 1'); 
                }  
                part 'Institution of Learning' : PhysicalComponent { 
                    doc /*


                    <p>An Institution of Learning is a facility dedicated to providing educational programs and services to its students. It can range from a school, college, university, academy, or other type of educational institution. A typical institution of learning includes classrooms, laboratories, libraries, and other facilities necessary for providing education. It also typically has faculty and staff members to help provide instruction and support to students. The purpose of such an institution is to provide a safe, secure, and nurturing environment for students to learn and grow. </p>

                    <p>References:
                    <ul>
                      <li>Begay, M. (2020). What Is an Institution of Learning?. Investopedia. Retrieved from https://www.investopedia.com/terms/i/institution-of-learning.asp</li>
                      <li>Bartolomé, A. (2020). What Is an Institution of Learning?. Verywell Family. Retrieved from https://www.verywellfamily.com/what-is-an-institution-of-learning-3144331</li>
                    </ul>
                    </p>
                    */ 
                    attribute :>> nature = PhysicalComponentNature::NODE; 
                    attribute :>> kind = PhysicalComponentKind::UNSET; 
                    attribute :>> isAbstract = false; 
                    attribute :>> isActor = true; 
                    attribute :>> isHuman = false; 
                    allocation 'a846a6a0-a1c6-4593-95ba-67ff56136c2c' : ComponentFunctionalAllocation
                        allocate function ::> 'CDT_System Project'::'CDT_System'::'Physical Architecture'::'Physical Functions'::'Root Physical Function'.'Aquire System'
                        to component ::> 'CDT_System Project'::'CDT_System'::'Physical Architecture'::'Structure'::'Institution of Learning';
                    perform 'CDT_System Project'::'CDT_System'::'Physical Architecture'::'Physical Functions'::'Root Physical Function'.'Aquire System' ; 
                    allocation '046bbe95-a3a6-45c0-8ac2-658faf3eaf36' : ComponentFunctionalAllocation
                        allocate function ::> 'CDT_System Project'::'CDT_System'::'Physical Architecture'::'Physical Functions'::'Root Physical Function'.'Report Received'
                        to component ::> 'CDT_System Project'::'CDT_System'::'Physical Architecture'::'Structure'::'Institution of Learning';
                    perform 'CDT_System Project'::'CDT_System'::'Physical Architecture'::'Physical Functions'::'Root Physical Function'.'Report Received' ; 
                    allocation 'd7a7b223-8026-43ab-9c42-30b42fd33435' : ComponentFunctionalAllocation
                        allocate function ::> 'CDT_System Project'::'CDT_System'::'Physical Architecture'::'Physical Functions'::'Root Physical Function'.'Established Concussion Policy'
                        to component ::> 'CDT_System Project'::'CDT_System'::'Physical Architecture'::'Structure'::'Institution of Learning';
                    perform 'CDT_System Project'::'CDT_System'::'Physical Architecture'::'Physical Functions'::'Root Physical Function'.'Established Concussion Policy' ; 
                    port 'PP 1' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                    }  
                    port 'CP 2' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation 'da991395-9d54-4b0a-89b6-ce03ff2921eb' : PortAllocation
                            allocate allocatedPort ::> 'CDT_System Project'::'CDT_System'::'Physical Architecture'::'Physical Functions'::'Root Physical Function'.'Report Received'.'inInstition Report'
                            to allocatingPort ::> 'CDT_System Project'::'CDT_System'::'Physical Architecture'::'Structure'::'Institution of Learning'.'CP 2'; 
                        ref :>> ownedPortAllocations =  ('CDT_System Project'::'CDT_System'::'Physical Architecture'::'Structure'::'Institution of Learning'.'CP 2'.'da991395-9d54-4b0a-89b6-ce03ff2921eb'); 
                    }  
                    ref :>> ownedFunctionalAllocation =  ('CDT_System Project'::'CDT_System'::'Physical Architecture'::'Structure'::'Institution of Learning'.'a846a6a0-a1c6-4593-95ba-67ff56136c2c',
                    'CDT_System Project'::'CDT_System'::'Physical Architecture'::'Structure'::'Institution of Learning'.'046bbe95-a3a6-45c0-8ac2-658faf3eaf36',
                    'CDT_System Project'::'CDT_System'::'Physical Architecture'::'Structure'::'Institution of Learning'.'d7a7b223-8026-43ab-9c42-30b42fd33435'); 
                     
                     
                }  
                part 'Parent' : PhysicalComponent { 
                    doc /*


                    <p>A parent is someone who takes on the responsibility of raising and caring for a child or children. As a parent, they provide physical and emotional support, guidance, and discipline to their children. Parents are expected to nurture and prepare their children for the future. <sup>[1](#myfootnote1)</sup></p>

                    <p>Parenting involves teaching children lessons on life and morality, such as teaching them how to interact with others in society, providing them with guidance in making important decisions, and setting rules and boundaries. Parents are also responsible for providing financial and emotional stability for their children. <sup>[2](#myfootnote2)</sup></p>

                    <p>Parenting is one of the most challenging and rewarding roles that a person can take on. It requires a great deal of dedication, patience, and love. Being a parent can be both a difficult and rewarding experience, and it is ultimately up to the parent to decide what type of parent they want to be. <sup>[3](#myfootnote3)</sup></p>

                    <p>

                    <sup id="myfootnote1">[1] (https://www.verywellfamily.com/what
                    */ 
                    attribute :>> nature = PhysicalComponentNature::NODE; 
                    attribute :>> kind = PhysicalComponentKind::UNSET; 
                    attribute :>> isAbstract = false; 
                    attribute :>> isActor = true; 
                    attribute :>> isHuman = false; 
                    allocation '08ff518f-7743-467e-bfe8-e89da2de9a09' : ComponentFunctionalAllocation
                        allocate function ::> 'CDT_System Project'::'CDT_System'::'Physical Architecture'::'Physical Functions'::'Root Physical Function'.'Report received'
                        to component ::> 'CDT_System Project'::'CDT_System'::'Physical Architecture'::'Structure'::'Parent';
                    perform 'CDT_System Project'::'CDT_System'::'Physical Architecture'::'Physical Functions'::'Root Physical Function'.'Report received' ; 
                    port 'PP 1' : PhysicalPort { 
                        attribute :>> isDerived = false; 
                        attribute :>> aggregationKind = AggregationKind::UNSET; 
                        attribute :>> isFinal = false; 
                        attribute :>> isPartOfKey = false; 
                        attribute :>> isMaxInclusive = false; 
                        attribute :>> isUnique = false; 
                        attribute :>> isMinInclusive = false; 
                        attribute :>> isReadOnly = false; 
                        attribute :>> isStatic = false; 
                        attribute :>> isOrdered = false; 
                        attribute :>> isAbstract = false; 
                    }  
                    port 'CP 2' : ComponentPort { 
                        attribute :>> isDerived = false; 
                        attribute :>> aggregationKind = AggregationKind::UNSET; 
                        attribute :>> isFinal = false; 
                        attribute :>> kind = ComponentPortKind::FLOW; 
                        attribute :>> isPartOfKey = false; 
                        attribute :>> isMaxInclusive = false; 
                        attribute :>> orientation = OrientationPortKind::IN; 
                        attribute :>> isUnique = false; 
                        attribute :>> isReadOnly = false; 
                        attribute :>> isMinInclusive = false; 
                        attribute :>> isStatic = false; 
                        attribute :>> isOrdered = false; 
                        attribute :>> isAbstract = false; 
                        ref allocation '6d55e632-4948-46b2-afd2-81f3df47d558' : PortAllocation
                            allocate allocatedPort ::> 'CDT_System Project'::'CDT_System'::'Physical Architecture'::'Physical Functions'::'Root Physical Function'.'Report received'.'inParen Report'
                            to allocatingPort ::> 'CDT_System Project'::'CDT_System'::'Physical Architecture'::'Structure'::'Parent'.'CP 2'; 
                        ref :>> ownedPortAllocations =  ('CDT_System Project'::'CDT_System'::'Physical Architecture'::'Structure'::'Parent'.'CP 2'.'6d55e632-4948-46b2-afd2-81f3df47d558'); 
                    }  
                    ref :>> ownedFunctionalAllocation =  ('CDT_System Project'::'CDT_System'::'Physical Architecture'::'Structure'::'Parent'.'08ff518f-7743-467e-bfe8-e89da2de9a09'); 
                     
                     
                }  
                constraint '55aab847-7979-4826-b3dd-054211598563' : CapellaConstraint { 
                    language "capella:linkedText" /*  */
                    
                    
                } 
                constraint 'Football Field' : CapellaConstraint { 
                    language "capella:linkedText" /*  */
                    
                } 
                constraint 'e397bc5c-0b81-4b68-adb0-fce811d7f169' : CapellaConstraint { 
                    language "capella:linkedText" /*  */
                    
                } 
                constraint '5f550592-f9dd-4677-8783-f4f876d840fd' : CapellaConstraint { 
                    language "capella:linkedText" /*  */
                    
                } 
                interface '45736a57-3b75-461d-8931-c878081818a9' : ComponentExchange 
                    connect source ::> 'CDT_System Project'::'CDT_System'::'Physical Architecture'::'Structure'::'Physical System'.'CDT App'.'To Trainer'
                    to  target ::> 'CDT_System Project'::'CDT_System'::'Physical Architecture'::'Structure'::'Trainer'.'CP 2' { 
                    attribute :>> isOriented = false; 
                    attribute :>> interfaceName = "App to trainer"; 
                    attribute :>> kind = ComponentExchangeKind::FLOW; 
                    allocation '084654d9-cae0-4220-b0d1-0296a8b51176' : ComponentExchangeFunctionalExchangeAllocation
                        allocate functionalExchange ::> 'CDT_System Project'::'CDT_System'::'Physical Architecture'::'Physical Functions'::'Root Physical Function'.'fb33a517-f686-437b-afcf-1bfaf8863b31'
                        to componentExchange ::> 'CDT_System Project'::'CDT_System'::'Physical Architecture'::'Structure'::'45736a57-3b75-461d-8931-c878081818a9'; 
                    allocation 'cbdbe241-a632-4919-b1d0-eec2ef445d58' : ComponentExchangeFunctionalExchangeAllocation
                        allocate functionalExchange ::> 'CDT_System Project'::'CDT_System'::'Physical Architecture'::'Physical Functions'::'Root Physical Function'.'06a84b77-2a20-41cc-9152-8af91456e9f7'
                        to componentExchange ::> 'CDT_System Project'::'CDT_System'::'Physical Architecture'::'Structure'::'45736a57-3b75-461d-8931-c878081818a9'; 
                    allocation '45684979-716c-4d2c-a0a3-b1d795bfdedf' : ComponentExchangeFunctionalExchangeAllocation
                        allocate functionalExchange ::> 'CDT_System Project'::'CDT_System'::'Physical Architecture'::'Physical Functions'::'Root Physical Function'.'497aee27-9576-4bc0-bf81-4968901d568b'
                        to componentExchange ::> 'CDT_System Project'::'CDT_System'::'Physical Architecture'::'Structure'::'45736a57-3b75-461d-8931-c878081818a9'; 
                    allocation '7e4c7cf6-bd21-4840-b3c2-be44bd7f8447' : ComponentExchangeFunctionalExchangeAllocation
                        allocate functionalExchange ::> 'CDT_System Project'::'CDT_System'::'Physical Architecture'::'Physical Functions'::'Root Physical Function'.'17084ce1-140b-4e28-9fdf-600155068998'
                        to componentExchange ::> 'CDT_System Project'::'CDT_System'::'Physical Architecture'::'Structure'::'45736a57-3b75-461d-8931-c878081818a9'; 
                    allocation '395b1c8f-3d58-4800-a622-98e75be42b3d' : ComponentExchangeFunctionalExchangeAllocation
                        allocate functionalExchange ::> 'CDT_System Project'::'CDT_System'::'Physical Architecture'::'Physical Functions'::'Root Physical Function'.'a8c90ff0-2958-40d5-988c-abcdfec9eb30'
                        to componentExchange ::> 'CDT_System Project'::'CDT_System'::'Physical Architecture'::'Structure'::'45736a57-3b75-461d-8931-c878081818a9'; 
                    allocation 'd4a09c3c-ce1d-457a-bc8b-065405c9d969' : ComponentExchangeFunctionalExchangeAllocation
                        allocate functionalExchange ::> 'CDT_System Project'::'CDT_System'::'Physical Architecture'::'Physical Functions'::'Root Physical Function'.'ac3ab92b-994d-4d14-9677-e9de084fb231'
                        to componentExchange ::> 'CDT_System Project'::'CDT_System'::'Physical Architecture'::'Structure'::'45736a57-3b75-461d-8931-c878081818a9'; 
                    ref :>> ownedComponentExchangeFunctionalExchangeAllocations =  ('CDT_System Project'::'CDT_System'::'Physical Architecture'::'Structure'::'45736a57-3b75-461d-8931-c878081818a9'.'084654d9-cae0-4220-b0d1-0296a8b51176',
                    'CDT_System Project'::'CDT_System'::'Physical Architecture'::'Structure'::'45736a57-3b75-461d-8931-c878081818a9'.'cbdbe241-a632-4919-b1d0-eec2ef445d58',
                    'CDT_System Project'::'CDT_System'::'Physical Architecture'::'Structure'::'45736a57-3b75-461d-8931-c878081818a9'.'45684979-716c-4d2c-a0a3-b1d795bfdedf',
                    'CDT_System Project'::'CDT_System'::'Physical Architecture'::'Structure'::'45736a57-3b75-461d-8931-c878081818a9'.'7e4c7cf6-bd21-4840-b3c2-be44bd7f8447',
                    'CDT_System Project'::'CDT_System'::'Physical Architecture'::'Structure'::'45736a57-3b75-461d-8931-c878081818a9'.'395b1c8f-3d58-4800-a622-98e75be42b3d',
                    'CDT_System Project'::'CDT_System'::'Physical Architecture'::'Structure'::'45736a57-3b75-461d-8931-c878081818a9'.'d4a09c3c-ce1d-457a-bc8b-065405c9d969'); 
                }  
                interface '4d7072b5-84b0-45e4-a6a0-e9e3c5d1075a' : ComponentExchange 
                    connect source ::> 'CDT_System Project'::'CDT_System'::'Physical Architecture'::'Structure'::'Physical System'.'Secure Application'.'CP 2'
                    to  target ::> 'CDT_System Project'::'CDT_System'::'Physical Architecture'::'Structure'::'Parent'.'CP 2' { 
                    attribute :>> isOriented = false; 
                    attribute :>> interfaceName = "SA to P"; 
                    attribute :>> kind = ComponentExchangeKind::FLOW; 
                    allocation '8eba4851-4543-408f-afcd-1e49efbecf6c' : ComponentExchangeFunctionalExchangeAllocation
                        allocate functionalExchange ::> 'CDT_System Project'::'CDT_System'::'Physical Architecture'::'Physical Functions'::'Root Physical Function'.'f0af47e2-b70f-4aad-b565-346bf3cfa078'
                        to componentExchange ::> 'CDT_System Project'::'CDT_System'::'Physical Architecture'::'Structure'::'4d7072b5-84b0-45e4-a6a0-e9e3c5d1075a'; 
                    ref :>> ownedComponentExchangeFunctionalExchangeAllocations =  ('CDT_System Project'::'CDT_System'::'Physical Architecture'::'Structure'::'4d7072b5-84b0-45e4-a6a0-e9e3c5d1075a'.'8eba4851-4543-408f-afcd-1e49efbecf6c'); 
                }  
                interface '1f68c19b-dd48-41f6-8f1c-fa3a6e3efd60' : ComponentExchange 
                    connect source ::> 'CDT_System Project'::'CDT_System'::'Physical Architecture'::'Structure'::'Physical System'.'Secure Application'.'CP 3'
                    to  target ::> 'CDT_System Project'::'CDT_System'::'Physical Architecture'::'Structure'::'Institution of Learning'.'CP 2' { 
                    attribute :>> isOriented = false; 
                    attribute :>> interfaceName = "SA to I"; 
                    attribute :>> kind = ComponentExchangeKind::FLOW; 
                    allocation 'ad1dea5d-c1d7-4476-bf80-1842fdb82c88' : ComponentExchangeFunctionalExchangeAllocation
                        allocate functionalExchange ::> 'CDT_System Project'::'CDT_System'::'Physical Architecture'::'Physical Functions'::'Root Physical Function'.'12ebf309-1bfb-49d3-b323-3f518edb7c44'
                        to componentExchange ::> 'CDT_System Project'::'CDT_System'::'Physical Architecture'::'Structure'::'1f68c19b-dd48-41f6-8f1c-fa3a6e3efd60'; 
                    ref :>> ownedComponentExchangeFunctionalExchangeAllocations =  ('CDT_System Project'::'CDT_System'::'Physical Architecture'::'Structure'::'1f68c19b-dd48-41f6-8f1c-fa3a6e3efd60'.'ad1dea5d-c1d7-4476-bf80-1842fdb82c88'); 
                }  
                interface 'c4e0b543-01f8-437f-861e-fb749adc8d4b' : ComponentExchange 
                    connect source ::> 'CDT_System Project'::'CDT_System'::'Physical Architecture'::'Structure'::'Physical System'.'Secure Application'.'CP 4'
                    to  target ::> 'CDT_System Project'::'CDT_System'::'Physical Architecture'::'Structure'::'Athlete'.'CP 3' { 
                    attribute :>> isOriented = false; 
                    attribute :>> interfaceName = "SA to Athlete"; 
                    attribute :>> kind = ComponentExchangeKind::FLOW; 
                    allocation 'd7efebb6-5de1-4a1a-ade1-dcbc48bfaddc' : ComponentExchangeFunctionalExchangeAllocation
                        allocate functionalExchange ::> 'CDT_System Project'::'CDT_System'::'Physical Architecture'::'Physical Functions'::'Root Physical Function'.'0cb04311-e193-4748-b3dd-d9e448d795ff'
                        to componentExchange ::> 'CDT_System Project'::'CDT_System'::'Physical Architecture'::'Structure'::'c4e0b543-01f8-437f-861e-fb749adc8d4b'; 
                    ref :>> ownedComponentExchangeFunctionalExchangeAllocations =  ('CDT_System Project'::'CDT_System'::'Physical Architecture'::'Structure'::'c4e0b543-01f8-437f-861e-fb749adc8d4b'.'d7efebb6-5de1-4a1a-ade1-dcbc48bfaddc'); 
                }  
                interface 'd3ff6ff7-8a77-4063-b64f-81586525ac97' : ComponentExchange 
                    connect source ::> 'CDT_System Project'::'CDT_System'::'Physical Architecture'::'Structure'::'Athlete'.'CP 4'
                    to  target ::> 'CDT_System Project'::'CDT_System'::'Physical Architecture'::'Structure'::'Physical System'.'Helmet'.'CP 1' { 
                    attribute :>> isOriented = false; 
                    attribute :>> interfaceName = "Athlete to Helmut"; 
                    attribute :>> kind = ComponentExchangeKind::FLOW; 
                    allocation '2ae9d10f-dbb3-4dcf-a09c-6ee52f565462' : ComponentExchangeFunctionalExchangeAllocation
                        allocate functionalExchange ::> 'CDT_System Project'::'CDT_System'::'Physical Architecture'::'Physical Functions'::'Root Physical Function'.'b4f7ef4b-c36e-4150-bd3b-d844d16b02ba'
                        to componentExchange ::> 'CDT_System Project'::'CDT_System'::'Physical Architecture'::'Structure'::'d3ff6ff7-8a77-4063-b64f-81586525ac97'; 
                    allocation 'a3f7f885-c12a-42ce-a419-1cdbfbb08d7d' : ComponentExchangeFunctionalExchangeAllocation
                        allocate functionalExchange ::> 'CDT_System Project'::'CDT_System'::'Physical Architecture'::'Physical Functions'::'Root Physical Function'.'9cf0b319-b000-4762-a282-3c1bc1f8d9f2'
                        to componentExchange ::> 'CDT_System Project'::'CDT_System'::'Physical Architecture'::'Structure'::'d3ff6ff7-8a77-4063-b64f-81586525ac97'; 
                    allocation '8f70067c-652f-4ff7-9318-24bc31663694' : ComponentExchangeFunctionalExchangeAllocation
                        allocate functionalExchange ::> 'CDT_System Project'::'CDT_System'::'Physical Architecture'::'Physical Functions'::'Root Physical Function'.'7f23244f-9558-4fef-b8bf-fb3cb5e42ddc'
                        to componentExchange ::> 'CDT_System Project'::'CDT_System'::'Physical Architecture'::'Structure'::'d3ff6ff7-8a77-4063-b64f-81586525ac97'; 
                    ref :>> ownedComponentExchangeFunctionalExchangeAllocations =  ('CDT_System Project'::'CDT_System'::'Physical Architecture'::'Structure'::'d3ff6ff7-8a77-4063-b64f-81586525ac97'.'2ae9d10f-dbb3-4dcf-a09c-6ee52f565462',
                    'CDT_System Project'::'CDT_System'::'Physical Architecture'::'Structure'::'d3ff6ff7-8a77-4063-b64f-81586525ac97'.'a3f7f885-c12a-42ce-a419-1cdbfbb08d7d',
                    'CDT_System Project'::'CDT_System'::'Physical Architecture'::'Structure'::'d3ff6ff7-8a77-4063-b64f-81586525ac97'.'8f70067c-652f-4ff7-9318-24bc31663694'); 
                }  
                interface '22b77700-803f-47e7-a00a-c5002310bd9b' : ComponentExchange 
                    connect source ::> 'CDT_System Project'::'CDT_System'::'Physical Architecture'::'Structure'::'Athlete'.'CP 7'
                    to  target ::> 'CDT_System Project'::'CDT_System'::'Physical Architecture'::'Structure'::'Physical System'.'Helmet'.'CP 3' { 
                    attribute :>> isOriented = false; 
                    attribute :>> interfaceName = "Activity"; 
                    attribute :>> kind = ComponentExchangeKind::FLOW; 
                }  
                interface '95f55b67-f5c9-47c1-b492-dfee90bdaffd' : ComponentExchange 
                    connect source ::> 'CDT_System Project'::'CDT_System'::'Physical Architecture'::'Structure'::'Athlete'.'CP 8'
                    to  target ::> 'CDT_System Project'::'CDT_System'::'Physical Architecture'::'Structure'::'Physical System'.'Sensing Device'.'CP 5' { 
                    attribute :>> isOriented = false; 
                    attribute :>> interfaceName = "Athlete to Sensor"; 
                    attribute :>> kind = ComponentExchangeKind::FLOW; 
                    allocation '79fbe3f5-1464-437a-8f79-05ffa6a1b211' : ComponentExchangeFunctionalExchangeAllocation
                        allocate functionalExchange ::> 'CDT_System Project'::'CDT_System'::'Physical Architecture'::'Physical Functions'::'Root Physical Function'.'7ce6b399-9ac1-4a1b-b0d8-408b5659bcd3'
                        to componentExchange ::> 'CDT_System Project'::'CDT_System'::'Physical Architecture'::'Structure'::'95f55b67-f5c9-47c1-b492-dfee90bdaffd'; 
                    allocation '3924e684-028b-452d-b793-5c25ef917410' : ComponentExchangeFunctionalExchangeAllocation
                        allocate functionalExchange ::> 'CDT_System Project'::'CDT_System'::'Physical Architecture'::'Physical Functions'::'Root Physical Function'.'95185f6a-8c82-4db9-a48c-b51e468be017'
                        to componentExchange ::> 'CDT_System Project'::'CDT_System'::'Physical Architecture'::'Structure'::'95f55b67-f5c9-47c1-b492-dfee90bdaffd'; 
                    ref :>> ownedComponentExchangeFunctionalExchangeAllocations =  ('CDT_System Project'::'CDT_System'::'Physical Architecture'::'Structure'::'95f55b67-f5c9-47c1-b492-dfee90bdaffd'.'79fbe3f5-1464-437a-8f79-05ffa6a1b211',
                    'CDT_System Project'::'CDT_System'::'Physical Architecture'::'Structure'::'95f55b67-f5c9-47c1-b492-dfee90bdaffd'.'3924e684-028b-452d-b793-5c25ef917410'); 
                }  
                interface '493be545-84f1-46b5-9be9-7e385503dec8' : PhysicalLink 
                    connect sourcePhysicalPort ::> 'CDT_System Project'::'CDT_System'::'Physical Architecture'::'Structure'::'Athlete'.'PP 1'
                    to targetPhysicalPort ::> 'CDT_System Project'::'CDT_System'::'Physical Architecture'::'Structure'::'Physical System'.'Helmet'.'PP 3' {
                    attribute :>> interfaceName = "Helmet Fit"; 
                     
                }  
                interface 'd81d7457-4d0c-4aa4-bdd8-6059cde7c84f' : PhysicalLink 
                    connect sourcePhysicalPort ::> 'CDT_System Project'::'CDT_System'::'Physical Architecture'::'Structure'::'Physical System'.'Router'.'TO MODEM'
                    to targetPhysicalPort ::> 'CDT_System Project'::'CDT_System'::'Physical Architecture'::'Structure'::'Physical System'.'Modem'.'To Router' {
                    attribute :>> interfaceName = "Cat 5"; 
                }  
                interface 'ef977895-351b-479c-a387-833a8fe98b51' : PhysicalLink 
                    connect sourcePhysicalPort ::> 'CDT_System Project'::'CDT_System'::'Physical Architecture'::'Structure'::'Physical System'.'Modem'.'To ISP'
                    to targetPhysicalPort ::> 'CDT_System Project'::'CDT_System'::'Physical Architecture'::'Structure'::'Physical System'.'ISP'.'To Modem' {
                    attribute :>> interfaceName = "Cable"; 
                }  
                interface '1946a7ce-7f1f-4107-83e8-e6882931cb44' : PhysicalLink 
                    connect sourcePhysicalPort ::> 'CDT_System Project'::'CDT_System'::'Physical Architecture'::'Structure'::'Physical System'.'IPAD'.'PP 2'
                    to targetPhysicalPort ::> 'CDT_System Project'::'CDT_System'::'Physical Architecture'::'Structure'::'Trainer'.'PP 1' {
                    attribute :>> interfaceName = "Visual"; 
                     
                }  
                interface '2a7dfe78-1734-4710-a9e3-2caac96df2ef' : PhysicalLink 
                    connect sourcePhysicalPort ::> 'CDT_System Project'::'CDT_System'::'Physical Architecture'::'Structure'::'Institution of Learning'.'PP 1'
                    to targetPhysicalPort ::> 'CDT_System Project'::'CDT_System'::'Physical Architecture'::'Structure'::'Physical System'.'Ipad'.'PP 2' {
                    attribute :>> interfaceName = "Visual"; 
                }  
                interface 'c6efef41-e456-4333-b6d9-b4f6d0982a38' : PhysicalLink 
                    connect sourcePhysicalPort ::> 'CDT_System Project'::'CDT_System'::'Physical Architecture'::'Structure'::'Physical System'.'Smartphone'.'PP 2'
                    to targetPhysicalPort ::> 'CDT_System Project'::'CDT_System'::'Physical Architecture'::'Structure'::'Parent'.'PP 1' {
                    attribute :>> interfaceName = "Visual"; 
                }  
                interface '7c2361eb-8b9b-4daa-9ee6-73d28eb56e0a' : PhysicalLink 
                    connect sourcePhysicalPort ::> 'CDT_System Project'::'CDT_System'::'Physical Architecture'::'Structure'::'Physical System'.'Athlete Smart Phone'.'PP 2'
                    to targetPhysicalPort ::> 'CDT_System Project'::'CDT_System'::'Physical Architecture'::'Structure'::'Athlete'.'PP 2' {
                    attribute :>> interfaceName = "Off Field Iphone"; 
                }  
                interface '363d3c22-085b-4c9a-a9c6-5a3e125ae0b2' : PhysicalLink 
                    connect sourcePhysicalPort ::> 'CDT_System Project'::'CDT_System'::'Physical Architecture'::'Structure'::'Physical System'.'Helmet'.'ID'.'PP 4'
                    to targetPhysicalPort ::> 'CDT_System Project'::'CDT_System'::'Physical Architecture'::'Structure'::'Athlete'.'PP 5' {
                    attribute :>> interfaceName = "ID Access"; 
                }  
                interface '25fbb7f7-cc78-4e28-84fe-7008a5e7e19a' : PhysicalLink 
                    connect sourcePhysicalPort ::> 'CDT_System Project'::'CDT_System'::'Physical Architecture'::'Structure'::'Athlete'.'PP 9'
                    to targetPhysicalPort ::> 'CDT_System Project'::'CDT_System'::'Physical Architecture'::'Structure'::'Physical System'.'Helmet'.'Sensor'.'PP 5' {
                    attribute :>> interfaceName = "M-Athlete to Sendor"; 
                     
                }  
            } 
        } 
    } 
    enum def 'ProgressStatus' :> EnumerationPropertyType  { 
        enum 'DRAFT'; 
        enum 'TO_BE_REVIEWED'; 
        enum 'TO_BE_DISCUSSED'; 
        enum 'REWORK_NECESSARY'; 
        enum 'UNDER_REWORK'; 
        enum 'REVIEWED_OK'; 
    }  
}
